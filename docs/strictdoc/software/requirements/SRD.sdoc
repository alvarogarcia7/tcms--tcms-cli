[DOCUMENT]
TITLE: Software Requirements Data
PREFIX: HLR-

[[SECTION]]
TITLE: Verifier Component Requirements

[REQUIREMENT]
UID: HLR-VER-001
TITLE: Execution Log Loading
STATEMENT: >>>
The verifier shall load execution logs from JSON files and parse them into in-memory
structures for comparison against test case definitions.
<<<
RELATIONS:
- TYPE: Parent
  VALUE: SYS-VER-001

[REQUIREMENT]
UID: HLR-VER-002
TITLE: Output Pattern Matching
STATEMENT: >>>
The verifier shall compare actual output against expected patterns using exact match,
regex match, and JSON schema validation strategies.
<<<
RELATIONS:
- TYPE: Parent
  VALUE: SYS-VER-002

[REQUIREMENT]
UID: HLR-VER-003
TITLE: Exit Code Verification
STATEMENT: >>>
The verifier shall verify step exit codes match expected values with optional range
or set matching.
<<<
RELATIONS:
- TYPE: Parent
  VALUE: SYS-VER-001

[REQUIREMENT]
UID: HLR-VER-004
TITLE: Detailed Mismatch Reporting
STATEMENT: >>>
When verification fails, the verifier shall report expected vs actual values with
character-level highlighting of differences.
<<<
RELATIONS:
- TYPE: Parent
  VALUE: SYS-VER-003

[REQUIREMENT]
UID: HLR-VER-005
TITLE: Batch Verification Orchestration
STATEMENT: >>>
The verifier shall orchestrate verification of multiple execution logs with aggregated
pass/fail counts and summary statistics.
<<<
RELATIONS:
- TYPE: Parent
  VALUE: SYS-VER-004

[[/SECTION]]

[[SECTION]]
TITLE: Test Case Content Requirements

[REQUIREMENT]
UID: HLR-TC-001
TITLE: Test Case Parsing
STATEMENT: >>>
The software shall parse test case YAML files extracting test_case_id, title,
sequences, steps, and metadata fields.
<<<
RELATIONS:
- TYPE: Parent
  VALUE: SYS-TC-001

[REQUIREMENT]
UID: HLR-TC-002
TITLE: Sequence Organization
STATEMENT: >>>
The software shall organize test steps into sequences with proper scoping of
variables and execution order guarantees.
<<<
RELATIONS:
- TYPE: Parent
  VALUE: SYS-TC-002

[REQUIREMENT]
UID: HLR-TC-003
TITLE: Step Command Storage
STATEMENT: >>>
The software shall store and retrieve test step commands with command metadata
(description, expected output, exit code).
<<<
RELATIONS:
- TYPE: Parent
  VALUE: SYS-TC-003

[REQUIREMENT]
UID: HLR-TC-004
TITLE: Variable Capture Configuration
STATEMENT: >>>
The software shall support regex-based and command-based variable capture with
specification of variable names and extraction patterns.
<<<
RELATIONS:
- TYPE: Parent
  VALUE: SYS-TC-004

[REQUIREMENT]
UID: HLR-TC-005
TITLE: Expected Output Configuration
STATEMENT: >>>
The software shall support configurable expected output with match type (exact, regex,
schema), comparison values, and optional flags.
<<<
RELATIONS:
- TYPE: Parent
  VALUE: SYS-TC-005

[REQUIREMENT]
UID: HLR-TC-006
TITLE: Prerequisite Management
STATEMENT: >>>
The software shall manage test prerequisites with type (manual/automatic), description,
verification commands, and completion status.
<<<
RELATIONS:
- TYPE: Parent
  VALUE: SYS-TC-006

[REQUIREMENT]
UID: HLR-TC-007
TITLE: Environment Variable Management
STATEMENT: >>>
The software shall manage required and optional environment variables with defaults,
validation, and substitution into test commands.
<<<
RELATIONS:
- TYPE: Parent
  VALUE: SYS-TC-007

[REQUIREMENT]
UID: HLR-TC-008
TITLE: Hook Point Configuration
STATEMENT: >>>
The software shall support configurable lifecycle hooks at eight execution points with
command specifications and error handling behavior.
<<<
RELATIONS:
- TYPE: Parent
  VALUE: SYS-TC-008

[[/SECTION]]

[[SECTION]]
TITLE: YAML Input/Output Requirements

[REQUIREMENT]
UID: HLR-YAML-001
TITLE: YAML Schema Resolution
STATEMENT: >>>
The software shall extract the schema field from YAML files and resolve it to the
appropriate JSON schema file for validation.
<<<
RELATIONS:
- TYPE: Parent
  VALUE: SYS-YAML-001

[REQUIREMENT]
UID: HLR-YAML-002
TITLE: YAML Type Detection
STATEMENT: >>>
The software shall extract the type field from YAML files to identify the content
type for appropriate processing and validation.
<<<
RELATIONS:
- TYPE: Parent
  VALUE: SYS-YAML-002

[REQUIREMENT]
UID: HLR-YAML-003
TITLE: Test Case YAML Loading
STATEMENT: >>>
The software shall deserialize test case YAML to TestCase structures with proper
handling of all supported fields and nesting.
<<<
RELATIONS:
- TYPE: Parent
  VALUE: SYS-YAML-003

[REQUIREMENT]
UID: HLR-YAML-004
TITLE: Execution Log JSON Escaping
STATEMENT: >>>
The software shall properly escape command output for JSON encoding using jq, custom
escaper, or shell fallback methods.
<<<
RELATIONS:
- TYPE: Parent
  VALUE: SYS-YAML-004

[REQUIREMENT]
UID: HLR-YAML-005
TITLE: Verification Result YAML Generation
STATEMENT: >>>
The software shall serialize verification results to YAML format with structured
output for all test sequences and steps.
<<<
RELATIONS:
- TYPE: Parent
  VALUE: SYS-YAML-005

[REQUIREMENT]
UID: HLR-YAML-006
TITLE: Container YAML Generation
STATEMENT: >>>
The software shall generate container YAML aggregating test metadata and verification
results for documentation generation.
<<<
RELATIONS:
- TYPE: Parent
  VALUE: SYS-YAML-006

[REQUIREMENT]
UID: HLR-YAML-007
TITLE: YAML Round-trip Preservation
STATEMENT: >>>
The software shall preserve test case information through YAML load/save cycles
without loss or modification.
<<<
RELATIONS:
- TYPE: Parent
  VALUE: SYS-YAML-007

[[/SECTION]]

[[SECTION]]
TITLE: Test Schema Requirements

[REQUIREMENT]
UID: HLR-SCHEMA-001
TITLE: Schema File Management
STATEMENT: >>>
The software shall load, cache, and serve JSON schema files for validation with
proper error handling for missing or malformed schemas.
<<<
RELATIONS:
- TYPE: Parent
  VALUE: SYS-SCHEMA-001

[REQUIREMENT]
UID: HLR-SCHEMA-002
TITLE: Schema Constraint Enforcement
STATEMENT: >>>
The software shall validate YAML content against schema constraints including required
fields, type constraints, and value restrictions.
<<<
RELATIONS:
- TYPE: Parent
  VALUE: SYS-SCHEMA-002

[REQUIREMENT]
UID: HLR-SCHEMA-003
TITLE: Nested Structure Validation
STATEMENT: >>>
The software shall recursively validate nested objects (sequences, steps, verifications)
against their schema definitions.
<<<
RELATIONS:
- TYPE: Parent
  VALUE: SYS-SCHEMA-003

[REQUIREMENT]
UID: HLR-SCHEMA-004
TITLE: Pattern Validation
STATEMENT: >>>
The software shall validate regex patterns and variable name formats against predefined
patterns to ensure syntactic correctness.
<<<
RELATIONS:
- TYPE: Parent
  VALUE: SYS-SCHEMA-004

[REQUIREMENT]
UID: HLR-SCHEMA-005
TITLE: Enumeration Validation
STATEMENT: >>>
The software shall validate enumerated field values against allowed enum sets defined
in the schema.
<<<
RELATIONS:
- TYPE: Parent
  VALUE: SYS-SCHEMA-005

[REQUIREMENT]
UID: HLR-SCHEMA-006
TITLE: Execution Log Schema Support
STATEMENT: >>>
The software shall use execution log schema to validate JSON execution output structure
and required fields.
<<<
RELATIONS:
- TYPE: Parent
  VALUE: SYS-SCHEMA-006

[REQUIREMENT]
UID: HLR-SCHEMA-007
TITLE: Verification Result Schema Support
STATEMENT: >>>
The software shall use verification result schema to validate container YAML structure
and compatibility.
<<<
RELATIONS:
- TYPE: Parent
  VALUE: SYS-SCHEMA-007

[REQUIREMENT]
UID: HLR-SCHEMA-008
TITLE: Validation Error Reporting
STATEMENT: >>>
The software shall report validation errors with specific field paths, constraint type,
expected value, and actual value.
<<<
RELATIONS:
- TYPE: Parent
  VALUE: SYS-SCHEMA-008

[[/SECTION]]

[[SECTION]]
TITLE: Executable Requirements

[REQUIREMENT]
UID: HLR-EXEC-VAL-001
TITLE: YAML Validator CLI
STATEMENT: >>>
The validate-yaml executable shall provide command-line interface for YAML validation.
<<<
RELATIONS:
- TYPE: Parent
  VALUE: SYS-EXEC-VAL-001

[REQUIREMENT]
UID: HLR-EXEC-VAL-002
TITLE: JSON Validator CLI
STATEMENT: >>>
The validate-json executable shall provide command-line interface for JSON validation.
<<<
RELATIONS:
- TYPE: Parent
  VALUE: SYS-EXEC-VAL-002

[REQUIREMENT]
UID: HLR-EXEC-GEN-001
TITLE: Test Executor CLI
STATEMENT: >>>
The test-executor executable shall provide commands for script generation and execution.
<<<
RELATIONS:
- TYPE: Parent
  VALUE: SYS-EXEC-GEN-001

[REQUIREMENT]
UID: HLR-EXEC-GEN-002
TITLE: JSON Escaper Utility
STATEMENT: >>>
The json-escape executable shall read from stdin and output JSON-escaped text.
<<<
RELATIONS:
- TYPE: Parent
  VALUE: SYS-EXEC-GEN-002

[REQUIREMENT]
UID: HLR-EXEC-GEN-003
TITLE: JSON to YAML Converter CLI
STATEMENT: >>>
The json-to-yaml executable shall convert JSON input to YAML output format.
<<<
RELATIONS:
- TYPE: Parent
  VALUE: SYS-EXEC-GEN-003

[REQUIREMENT]
UID: HLR-EXEC-GEN-004
TITLE: Script Cleanup Utility
STATEMENT: >>>
The script-cleanup executable shall remove generated test scripts and artifacts.
<<<
RELATIONS:
- TYPE: Parent
  VALUE: SYS-EXEC-GEN-004

[REQUIREMENT]
UID: HLR-EXEC-ORCH-001
TITLE: Test Orchestrator CLI
STATEMENT: >>>
The test-orchestrator executable shall manage test execution and sequence coordination.
<<<
RELATIONS:
- TYPE: Parent
  VALUE: SYS-EXEC-ORCH-001

[REQUIREMENT]
UID: HLR-EXEC-ORCH-002
TITLE: Testcase Manager CLI
STATEMENT: >>>
The testcase-manager executable shall provide test case lifecycle management commands.
<<<
RELATIONS:
- TYPE: Parent
  VALUE: SYS-EXEC-ORCH-002

[REQUIREMENT]
UID: HLR-EXEC-ORCH-003
TITLE: Test Run Manager CLI
STATEMENT: >>>
The test-run-manager executable shall manage test run execution and status tracking.
<<<
RELATIONS:
- TYPE: Parent
  VALUE: SYS-EXEC-ORCH-003

[REQUIREMENT]
UID: HLR-EXEC-VER-001
TITLE: Verifier CLI
STATEMENT: >>>
The verifier executable shall provide verification commands with result generation.
<<<
RELATIONS:
- TYPE: Parent
  VALUE: SYS-EXEC-VER-001

[REQUIREMENT]
UID: HLR-EXEC-VER-002
TITLE: TPDG Compatibility Tool CLI
STATEMENT: >>>
The tpdg-compat executable shall validate container YAML compatibility.
<<<
RELATIONS:
- TYPE: Parent
  VALUE: SYS-EXEC-VER-002

[REQUIREMENT]
UID: HLR-EXEC-EDT-001
TITLE: Editor Terminal UI
STATEMENT: >>>
The editor executable shall provide interactive terminal UI for test case editing.
<<<
RELATIONS:
- TYPE: Parent
  VALUE: SYS-EXEC-EDT-001

[REQUIREMENT]
UID: HLR-VER-006
TITLE: Mismatch Detail Analysis
STATEMENT: >>>
The verifier shall provide detailed analysis of output mismatches including character-level
differences, line-by-line comparisons, and visual highlighting of divergences.
<<<
RELATIONS:
- TYPE: Parent
  VALUE: SYS-VER-003

[REQUIREMENT]
UID: HLR-VER-007
TITLE: Test Result Aggregation
STATEMENT: >>>
The verifier shall aggregate verification results from multiple test cases and generate
comprehensive summary reports with pass/fail statistics and success rates.
<<<
RELATIONS:
- TYPE: Parent
  VALUE: SYS-VER-004

[REQUIREMENT]
UID: HLR-VER-008
TITLE: Verification Logging
STATEMENT: >>>
The verifier shall record all verification steps with timestamps and provide detailed
audit trails of comparison operations.
<<<
RELATIONS:
- TYPE: Parent
  VALUE: SYS-VER-005

[REQUIREMENT]
UID: HLR-TC-009
TITLE: Step Command Validation
STATEMENT: >>>
The software shall validate step commands for proper shell syntax and detect potential
issues before test execution.
<<<
RELATIONS:
- TYPE: Parent
  VALUE: SYS-TC-003

[REQUIREMENT]
UID: HLR-TC-010
TITLE: Variable Capture Patterns
STATEMENT: >>>
The software shall support multiple variable capture patterns including regex extraction,
command substitution, and JSON path selection.
<<<
RELATIONS:
- TYPE: Parent
  VALUE: SYS-TC-004

[REQUIREMENT]
UID: HLR-TC-011
TITLE: Expected Output Specification
STATEMENT: >>>
The software shall allow flexible expected output specification with support for exact
matching, regex patterns, and JSON schema validation.
<<<
RELATIONS:
- TYPE: Parent
  VALUE: SYS-TC-005

[REQUIREMENT]
UID: HLR-TC-012
TITLE: Prerequisite Verification
STATEMENT: >>>
The software shall verify all prerequisites before test execution and report prerequisite
failures with detailed reasons.
<<<
RELATIONS:
- TYPE: Parent
  VALUE: SYS-TC-006

[REQUIREMENT]
UID: HLR-TC-013
TITLE: Environment Variable Validation
STATEMENT: >>>
The software shall validate that all required environment variables are present and
correctly formatted before executing tests.
<<<
RELATIONS:
- TYPE: Parent
  VALUE: SYS-TC-007

[REQUIREMENT]
UID: HLR-TC-014
TITLE: Lifecycle Hook Execution
STATEMENT: >>>
The software shall execute lifecycle hooks at all eight defined lifecycle points with
proper error handling and context passing.
<<<
RELATIONS:
- TYPE: Parent
  VALUE: SYS-TC-008

[REQUIREMENT]
UID: HLR-YAML-008
TITLE: YAML Schema Extraction
STATEMENT: >>>
The software shall extract schema field from YAML files and use it to automatically
resolve the appropriate JSON schema for validation.
<<<
RELATIONS:
- TYPE: Parent
  VALUE: SYS-YAML-001

[REQUIREMENT]
UID: HLR-YAML-009
TITLE: YAML Content Type Detection
STATEMENT: >>>
The software shall extract and use the type field from YAML files to determine the
correct processing pipeline for the content.
<<<
RELATIONS:
- TYPE: Parent
  VALUE: SYS-YAML-002

[REQUIREMENT]
UID: HLR-YAML-010
TITLE: Test Case YAML Deserialization
STATEMENT: >>>
The software shall deserialize test case YAML files into structured TestCase objects
with full support for all nested fields and sequences.
<<<
RELATIONS:
- TYPE: Parent
  VALUE: SYS-YAML-003

[REQUIREMENT]
UID: HLR-YAML-011
TITLE: JSON Output Escaping
STATEMENT: >>>
The software shall properly escape command output for JSON encoding using the most
robust method available (jq, json-escape, or shell fallback).
<<<
RELATIONS:
- TYPE: Parent
  VALUE: SYS-YAML-004

[REQUIREMENT]
UID: HLR-YAML-012
TITLE: Verification Result Serialization
STATEMENT: >>>
The software shall serialize verification results to YAML format with all metadata,
step results, and comparison details preserved.
<<<
RELATIONS:
- TYPE: Parent
  VALUE: SYS-YAML-005

[REQUIREMENT]
UID: HLR-YAML-013
TITLE: Container YAML Generation
STATEMENT: >>>
The software shall generate container YAML files that aggregate test metadata and
verification results for documentation generation.
<<<
RELATIONS:
- TYPE: Parent
  VALUE: SYS-YAML-006

[REQUIREMENT]
UID: HLR-YAML-014
TITLE: YAML Data Integrity
STATEMENT: >>>
The software shall preserve all test case information through YAML load-save cycles
without loss, corruption, or modification.
<<<
RELATIONS:
- TYPE: Parent
  VALUE: SYS-YAML-007

[REQUIREMENT]
UID: HLR-SCHEMA-009
TITLE: Schema File Caching
STATEMENT: >>>
The software shall load, cache, and efficiently serve JSON schema files for validation
with proper invalidation on schema changes.
<<<
RELATIONS:
- TYPE: Parent
  VALUE: SYS-SCHEMA-001

[REQUIREMENT]
UID: HLR-SCHEMA-010
TITLE: Schema Constraint Validation
STATEMENT: >>>
The software shall validate YAML content against all schema constraints including
required properties, types, and value restrictions.
<<<
RELATIONS:
- TYPE: Parent
  VALUE: SYS-SCHEMA-002

[REQUIREMENT]
UID: HLR-SCHEMA-011
TITLE: Recursive Structure Validation
STATEMENT: >>>
The software shall recursively validate nested objects such as sequences and steps
against their respective schema definitions.
<<<
RELATIONS:
- TYPE: Parent
  VALUE: SYS-SCHEMA-003

[REQUIREMENT]
UID: HLR-SCHEMA-012
TITLE: Pattern Syntax Validation
STATEMENT: >>>
The software shall validate regex patterns and variable name formats for syntactic
correctness according to predefined pattern specifications.
<<<
RELATIONS:
- TYPE: Parent
  VALUE: SYS-SCHEMA-004

[REQUIREMENT]
UID: HLR-SCHEMA-013
TITLE: Enumeration Constraint Validation
STATEMENT: >>>
The software shall validate that enumerated field values match allowed enum sets
defined in the schema with detailed error reporting.
<<<
RELATIONS:
- TYPE: Parent
  VALUE: SYS-SCHEMA-005

[REQUIREMENT]
UID: HLR-SCHEMA-014
TITLE: Execution Log Format Validation
STATEMENT: >>>
The software shall use execution log schema to validate JSON execution output structure
including all required fields and data types.
<<<
RELATIONS:
- TYPE: Parent
  VALUE: SYS-SCHEMA-006

[REQUIREMENT]
UID: HLR-SCHEMA-015
TITLE: Verification Result Format Validation
STATEMENT: >>>
The software shall use verification result schema to validate container YAML structure
and ensure compatibility with documentation generators.
<<<
RELATIONS:
- TYPE: Parent
  VALUE: SYS-SCHEMA-007

[REQUIREMENT]
UID: HLR-SCHEMA-016
TITLE: Schema Error Reporting
STATEMENT: >>>
The software shall report validation errors with specific field paths, constraint types,
expected values, and actual values for debugging.
<<<
RELATIONS:
- TYPE: Parent
  VALUE: SYS-SCHEMA-008

[REQUIREMENT]
UID: HLR-JE-001
TITLE: JSON String Escaping Implementation
STATEMENT: >>>
The json-escape component shall read plain text from stdin and produce valid JSON-escaped
strings suitable for embedding in JSON field values.
<<<
RELATIONS:
- TYPE: Parent
  VALUE: SYS-JE-001

[REQUIREMENT]
UID: HLR-JE-002
TITLE: Special Character Escape Handling
STATEMENT: >>>
The escaping algorithm shall handle all JSON-required escape sequences including quotes,
backslashes, newlines, tabs, and control codes.
<<<
RELATIONS:
- TYPE: Parent
  VALUE: SYS-JE-002

[REQUIREMENT]
UID: HLR-J2Y-001
TITLE: JSON Parsing and Structure Detection
STATEMENT: >>>
The converter shall parse JSON input and detect the structure type (batch array, container
object, or single test case) for appropriate handling.
<<<
RELATIONS:
- TYPE: Parent
  VALUE: SYS-J2Y-001

[REQUIREMENT]
UID: HLR-J2Y-002
TITLE: YAML Output File Generation
STATEMENT: >>>
The converter shall create properly formatted YAML output files with correct naming
conventions based on test_case_id and directory structure.
<<<
RELATIONS:
- TYPE: Parent
  VALUE: SYS-J2Y-003

[REQUIREMENT]
UID: HLR-VJ-001
TITLE: JSON Schema Validation Engine
STATEMENT: >>>
The validator shall compile and apply JSON schemas to validate payload documents
against defined constraints and required properties.
<<<
RELATIONS:
- TYPE: Parent
  VALUE: SYS-VJ-001

[REQUIREMENT]
UID: HLR-VJ-002
TITLE: Schema Path Resolution
STATEMENT: >>>
The auto-resolution mechanism shall extract the schema field from JSON payloads and
resolve relative paths to locate actual schema files.
<<<
RELATIONS:
- TYPE: Parent
  VALUE: SYS-VJ-002

[REQUIREMENT]
UID: HLR-VJ-003
TITLE: Constraint Violation Reporting
STATEMENT: >>>
On validation failure, the validator shall report each constraint violation with JSON
pointer path, actual value, and expected constraint description.
<<<
RELATIONS:
- TYPE: Parent
  VALUE: SYS-VJ-004

[REQUIREMENT]
UID: HLR-VY-001
TITLE: Multiple File Validation Coordination
STATEMENT: >>>
The validator shall coordinate validation of multiple YAML files with aggregated results
and summary statistics reporting.
<<<
RELATIONS:
- TYPE: Parent
  VALUE: SYS-VY-009

[REQUIREMENT]
UID: HLR-VY-002
TITLE: Incremental Validation Processing
STATEMENT: >>>
The validator shall support incremental validation for large test suites with change
detection and targeted re-validation.
<<<
RELATIONS:
- TYPE: Parent
  VALUE: SYS-VY-010

[REQUIREMENT]
UID: HLR-TP-001
TITLE: Container YAML Structure Validation
STATEMENT: >>>
The compatibility checker shall validate container YAML structure including test_results
array and all nested test result objects.
<<<
RELATIONS:
- TYPE: Parent
  VALUE: SYS-TP-011

[REQUIREMENT]
UID: HLR-TP-002
TITLE: Batch File Processing Framework
STATEMENT: >>>
The batch processor shall discover YAML files matching patterns, validate each independently,
collect results, and generate aggregated reports.
<<<
RELATIONS:
- TYPE: Parent
  VALUE: SYS-TP-012

[REQUIREMENT]
UID: HLR-TEX-001
TITLE: Bash Script Generation from YAML
STATEMENT: >>>
The generator shall parse YAML test cases and generate bash scripts with proper variable
substitution, command execution, and output capture.
<<<
RELATIONS:
- TYPE: Parent
  VALUE: SYS-TEX-011

[REQUIREMENT]
UID: HLR-TEX-002
TITLE: Test Execution and JSON Logging
STATEMENT: >>>
The executor shall run generated scripts, capture output with timestamps, and serialize
results to JSON format for verification.
<<<
RELATIONS:
- TYPE: Parent
  VALUE: SYS-TEX-012

[REQUIREMENT]
UID: HLR-TO-001
TITLE: Parallel Test Execution Management
STATEMENT: >>>
The orchestrator shall manage worker thread pool, distribute test cases, coordinate
execution, and aggregate results.
<<<
RELATIONS:
- TYPE: Parent
  VALUE: SYS-TO-009

[REQUIREMENT]
UID: HLR-TO-002
TITLE: Exponential Backoff Retry Engine
STATEMENT: >>>
The retry engine shall implement configurable backoff delays, track retry attempts,
and respect maximum retry limits.
<<<
RELATIONS:
- TYPE: Parent
  VALUE: SYS-TO-010

[REQUIREMENT]
UID: HLR-TRM-001
TITLE: Test Run Record Persistence
STATEMENT: >>>
The manager shall serialize and deserialize test run objects with execution metadata
and timestamp tracking.
<<<
RELATIONS:
- TYPE: Parent
  VALUE: SYS-TRV-007

[REQUIREMENT]
UID: HLR-TRM-002
TITLE: Test Run Retrieval and Filtering
STATEMENT: >>>
The retrieval system shall load all test runs from storage, apply filter criteria,
and organize results by test case.
<<<
RELATIONS:
- TYPE: Parent
  VALUE: SYS-TRV-008

[REQUIREMENT]
UID: HLR-TVR-001
TITLE: Execution Log Parsing and Loading
STATEMENT: >>>
The parser shall read and deserialize JSON execution logs extracting test metadata
and step results into structured format.
<<<
RELATIONS:
- TYPE: Parent
  VALUE: SYS-TVR-008

[REQUIREMENT]
UID: HLR-TVR-002
TITLE: Batch Verification Coordination
STATEMENT: >>>
The coordinator shall process multiple execution logs, verify each against test cases,
and aggregate verification results.
<<<
RELATIONS:
- TYPE: Parent
  VALUE: SYS-TVR-009

[REQUIREMENT]
UID: HLR-SC-001
TITLE: Output Normalization Pipeline
STATEMENT: >>>
The cleaner shall identify and remove ANSI escape sequences and control characters
from script capture output.
<<<
RELATIONS:
- TYPE: Parent
  VALUE: SYS-SC-006

[REQUIREMENT]
UID: HLR-ED-001
TITLE: Interactive Terminal UI Framework
STATEMENT: >>>
The editor shall implement interactive terminal interface using curses library with
menus, input fields, and real-time validation.
<<<
RELATIONS:
- TYPE: Parent
  VALUE: SYS-ED-011

[REQUIREMENT]
UID: HLR-ED-002
TITLE: Test Case State Management
STATEMENT: >>>
The manager shall synchronize UI state with YAML file content and detect unsaved changes.
<<<
RELATIONS:
- TYPE: Parent
  VALUE: SYS-ED-012

[REQUIREMENT]
UID: HLR-ED-003
TITLE: Fuzzy Search Engine
STATEMENT: >>>
The search engine shall implement fuzzy matching for test case selection with configurable
scoring.
<<<
RELATIONS:
- TYPE: Parent
  VALUE: SYS-ED-013

[REQUIREMENT]
UID: HLR-AV-001
TITLE: SHA-256 Hash Computation
STATEMENT: >>>
The hasher shall compute SHA-256 digest of YAML file content and format result in
hex notation.
<<<
RELATIONS:
- TYPE: Parent
  VALUE: SYS-AV-009

[REQUIREMENT]
UID: HLR-AV-002
TITLE: ECDSA P-521 Signature Generation
STATEMENT: >>>
The signer shall sign hashes using P-521 ECDSA private key and encode signature in
base64 format for JSON serialization.
<<<
RELATIONS:
- TYPE: Parent
  VALUE: SYS-AV-010

[REQUIREMENT]
UID: HLR-INT-001
TITLE: Standard Data Format Specification
STATEMENT: >>>
The framework shall define standard YAML/JSON structures for data exchange between
executables with documented schemas.
<<<
RELATIONS:
- TYPE: Parent
  VALUE: SYS-INT-001

[REQUIREMENT]
UID: HLR-INT-002
TITLE: Unified Error Code Mapping
STATEMENT: >>>
The error mapping shall define consistent exit codes: 0=success, 1=validation error,
2=runtime error, 3=configuration error.
<<<
RELATIONS:
- TYPE: Parent
  VALUE: SYS-INT-002

[REQUIREMENT]
UID: HLR-INT-003
TITLE: Logging Framework Abstraction Layer
STATEMENT: >>>
The logging layer shall abstract env_logger with standard functions and support
RUST_LOG environment variable.
<<<
RELATIONS:
- TYPE: Parent
  VALUE: SYS-INT-003

[REQUIREMENT]
UID: HLR-INT-004
TITLE: Configuration File Standardization
STATEMENT: >>>
All configuration files shall use TOML or YAML format with documented schemas for
consistency.
<<<
RELATIONS:
- TYPE: Parent
  VALUE: SYS-INT-004

[REQUIREMENT]
UID: HLR-INT-005
TITLE: Help and Version Support
STATEMENT: >>>
All executables shall provide comprehensive help via --help and semantic versioning
via --version.
<<<
RELATIONS:
- TYPE: Parent
  VALUE: SYS-INT-005

[REQUIREMENT]
UID: HLR-PERF-001
TITLE: Streaming and Memory Efficiency
STATEMENT: >>>
Large file handling shall use streaming readers to process content in chunks rather
than loading entire files into memory.
<<<
RELATIONS:
- TYPE: Parent
  VALUE: SYS-PERF-001

[REQUIREMENT]
UID: HLR-PERF-002
TITLE: Parallel Processing Optimization
STATEMENT: >>>
Parallel execution shall minimize synchronization overhead and implement dynamic load
balancing strategies.
<<<
RELATIONS:
- TYPE: Parent
  VALUE: SYS-PERF-002

[REQUIREMENT]
UID: HLR-PERF-003
TITLE: Incremental Compilation Caching
STATEMENT: >>>
Build system shall leverage incremental compilation caching for faster builds and
dependency-based rebuild optimization.
<<<
RELATIONS:
- TYPE: Parent
  VALUE: SYS-PERF-003

[REQUIREMENT]
UID: HLR-REL-001
TITLE: Graceful Error Handling Implementation
STATEMENT: >>>
All components shall implement comprehensive try-catch blocks and return descriptive
error messages.
<<<
RELATIONS:
- TYPE: Parent
  VALUE: SYS-REL-001

[REQUIREMENT]
UID: HLR-REL-002
TITLE: Atomic File Write Operations
STATEMENT: >>>
File write operations shall use atomic patterns: write to temporary file, then rename
to target to ensure consistency.
<<<
RELATIONS:
- TYPE: Parent
  VALUE: SYS-REL-002

[REQUIREMENT]
UID: HLR-VER-011
TITLE: Advanced Verification Feature 11
STATEMENT: >>>
The verification system shall support feature variant 11 for comprehensive output analysis.
<<<
RELATIONS:
- TYPE: Parent
  VALUE: SYS-VER-005

[REQUIREMENT]
UID: HLR-VER-012
TITLE: Advanced Verification Feature 12
STATEMENT: >>>
The verification system shall support feature variant 12 for comprehensive output analysis.
<<<
RELATIONS:
- TYPE: Parent
  VALUE: SYS-VER-005

[REQUIREMENT]
UID: HLR-VER-013
TITLE: Advanced Verification Feature 13
STATEMENT: >>>
The verification system shall support feature variant 13 for comprehensive output analysis.
<<<
RELATIONS:
- TYPE: Parent
  VALUE: SYS-VER-005

[REQUIREMENT]
UID: HLR-VER-014
TITLE: Advanced Verification Feature 14
STATEMENT: >>>
The verification system shall support feature variant 14 for comprehensive output analysis.
<<<
RELATIONS:
- TYPE: Parent
  VALUE: SYS-VER-005

[REQUIREMENT]
UID: HLR-VER-015
TITLE: Advanced Verification Feature 15
STATEMENT: >>>
The verification system shall support feature variant 15 for comprehensive output analysis.
<<<
RELATIONS:
- TYPE: Parent
  VALUE: SYS-VER-005

[REQUIREMENT]
UID: HLR-VER-016
TITLE: Advanced Verification Feature 16
STATEMENT: >>>
The verification system shall support feature variant 16 for comprehensive output analysis.
<<<
RELATIONS:
- TYPE: Parent
  VALUE: SYS-VER-005

[REQUIREMENT]
UID: HLR-VER-017
TITLE: Advanced Verification Feature 17
STATEMENT: >>>
The verification system shall support feature variant 17 for comprehensive output analysis.
<<<
RELATIONS:
- TYPE: Parent
  VALUE: SYS-VER-005

[REQUIREMENT]
UID: HLR-VER-018
TITLE: Advanced Verification Feature 18
STATEMENT: >>>
The verification system shall support feature variant 18 for comprehensive output analysis.
<<<
RELATIONS:
- TYPE: Parent
  VALUE: SYS-VER-005

[REQUIREMENT]
UID: HLR-VER-019
TITLE: Advanced Verification Feature 19
STATEMENT: >>>
The verification system shall support feature variant 19 for comprehensive output analysis.
<<<
RELATIONS:
- TYPE: Parent
  VALUE: SYS-VER-005

[REQUIREMENT]
UID: HLR-TC-019
TITLE: Test Case Feature 19
STATEMENT: >>>
Test case framework shall support advanced feature 19 for flexible test definition.
<<<
RELATIONS:
- TYPE: Parent
  VALUE: SYS-TC-008

[REQUIREMENT]
UID: HLR-TC-020
TITLE: Test Case Feature 20
STATEMENT: >>>
Test case framework shall support advanced feature 20 for flexible test definition.
<<<
RELATIONS:
- TYPE: Parent
  VALUE: SYS-TC-008

[REQUIREMENT]
UID: HLR-TC-021
TITLE: Test Case Feature 21
STATEMENT: >>>
Test case framework shall support advanced feature 21 for flexible test definition.
<<<
RELATIONS:
- TYPE: Parent
  VALUE: SYS-TC-008

[REQUIREMENT]
UID: HLR-TC-022
TITLE: Test Case Feature 22
STATEMENT: >>>
Test case framework shall support advanced feature 22 for flexible test definition.
<<<
RELATIONS:
- TYPE: Parent
  VALUE: SYS-TC-008

[REQUIREMENT]
UID: HLR-TC-023
TITLE: Test Case Feature 23
STATEMENT: >>>
Test case framework shall support advanced feature 23 for flexible test definition.
<<<
RELATIONS:
- TYPE: Parent
  VALUE: SYS-TC-008

[REQUIREMENT]
UID: HLR-TC-024
TITLE: Test Case Feature 24
STATEMENT: >>>
Test case framework shall support advanced feature 24 for flexible test definition.
<<<
RELATIONS:
- TYPE: Parent
  VALUE: SYS-TC-008

[REQUIREMENT]
UID: HLR-TC-025
TITLE: Test Case Feature 25
STATEMENT: >>>
Test case framework shall support advanced feature 25 for flexible test definition.
<<<
RELATIONS:
- TYPE: Parent
  VALUE: SYS-TC-008

[REQUIREMENT]
UID: HLR-TC-026
TITLE: Test Case Feature 26
STATEMENT: >>>
Test case framework shall support advanced feature 26 for flexible test definition.
<<<
RELATIONS:
- TYPE: Parent
  VALUE: SYS-TC-008

[REQUIREMENT]
UID: HLR-TC-027
TITLE: Test Case Feature 27
STATEMENT: >>>
Test case framework shall support advanced feature 27 for flexible test definition.
<<<
RELATIONS:
- TYPE: Parent
  VALUE: SYS-TC-008

[REQUIREMENT]
UID: HLR-TC-028
TITLE: Test Case Feature 28
STATEMENT: >>>
Test case framework shall support advanced feature 28 for flexible test definition.
<<<
RELATIONS:
- TYPE: Parent
  VALUE: SYS-TC-008

[REQUIREMENT]
UID: HLR-TC-029
TITLE: Test Case Feature 29
STATEMENT: >>>
Test case framework shall support advanced feature 29 for flexible test definition.
<<<
RELATIONS:
- TYPE: Parent
  VALUE: SYS-TC-008

[REQUIREMENT]
UID: HLR-TC-030
TITLE: Test Case Feature 30
STATEMENT: >>>
Test case framework shall support advanced feature 30 for flexible test definition.
<<<
RELATIONS:
- TYPE: Parent
  VALUE: SYS-TC-008

[REQUIREMENT]
UID: HLR-TC-031
TITLE: Test Case Feature 31
STATEMENT: >>>
Test case framework shall support advanced feature 31 for flexible test definition.
<<<
RELATIONS:
- TYPE: Parent
  VALUE: SYS-TC-008

[REQUIREMENT]
UID: HLR-TC-032
TITLE: Test Case Feature 32
STATEMENT: >>>
Test case framework shall support advanced feature 32 for flexible test definition.
<<<
RELATIONS:
- TYPE: Parent
  VALUE: SYS-TC-008

[REQUIREMENT]
UID: HLR-TC-033
TITLE: Test Case Feature 33
STATEMENT: >>>
Test case framework shall support advanced feature 33 for flexible test definition.
<<<
RELATIONS:
- TYPE: Parent
  VALUE: SYS-TC-008

[REQUIREMENT]
UID: HLR-TC-034
TITLE: Test Case Feature 34
STATEMENT: >>>
Test case framework shall support advanced feature 34 for flexible test definition.
<<<
RELATIONS:
- TYPE: Parent
  VALUE: SYS-TC-008

[REQUIREMENT]
UID: HLR-TC-035
TITLE: Test Case Feature 35
STATEMENT: >>>
Test case framework shall support advanced feature 35 for flexible test definition.
<<<
RELATIONS:
- TYPE: Parent
  VALUE: SYS-TC-008

[REQUIREMENT]
UID: HLR-TC-036
TITLE: Test Case Feature 36
STATEMENT: >>>
Test case framework shall support advanced feature 36 for flexible test definition.
<<<
RELATIONS:
- TYPE: Parent
  VALUE: SYS-TC-008

[REQUIREMENT]
UID: HLR-TC-037
TITLE: Test Case Feature 37
STATEMENT: >>>
Test case framework shall support advanced feature 37 for flexible test definition.
<<<
RELATIONS:
- TYPE: Parent
  VALUE: SYS-TC-008

[REQUIREMENT]
UID: HLR-TC-038
TITLE: Test Case Feature 38
STATEMENT: >>>
Test case framework shall support advanced feature 38 for flexible test definition.
<<<
RELATIONS:
- TYPE: Parent
  VALUE: SYS-TC-008

[REQUIREMENT]
UID: HLR-TC-039
TITLE: Test Case Feature 39
STATEMENT: >>>
Test case framework shall support advanced feature 39 for flexible test definition.
<<<
RELATIONS:
- TYPE: Parent
  VALUE: SYS-TC-008

[REQUIREMENT]
UID: HLR-JE-007
TITLE: JSON Escape Feature 7
STATEMENT: >>>
The JSON Escape component shall support feature variant 7.
<<<
RELATIONS:
- TYPE: Parent
  VALUE: SYS-JE-006

[REQUIREMENT]
UID: HLR-JE-008
TITLE: JSON Escape Feature 8
STATEMENT: >>>
The JSON Escape component shall support feature variant 8.
<<<
RELATIONS:
- TYPE: Parent
  VALUE: SYS-JE-006

[REQUIREMENT]
UID: HLR-JE-009
TITLE: JSON Escape Feature 9
STATEMENT: >>>
The JSON Escape component shall support feature variant 9.
<<<
RELATIONS:
- TYPE: Parent
  VALUE: SYS-JE-006

[REQUIREMENT]
UID: HLR-JE-010
TITLE: JSON Escape Feature 10
STATEMENT: >>>
The JSON Escape component shall support feature variant 10.
<<<
RELATIONS:
- TYPE: Parent
  VALUE: SYS-JE-006

[REQUIREMENT]
UID: HLR-JE-011
TITLE: JSON Escape Feature 11
STATEMENT: >>>
The JSON Escape component shall support feature variant 11.
<<<
RELATIONS:
- TYPE: Parent
  VALUE: SYS-JE-006

[REQUIREMENT]
UID: HLR-JE-012
TITLE: JSON Escape Feature 12
STATEMENT: >>>
The JSON Escape component shall support feature variant 12.
<<<
RELATIONS:
- TYPE: Parent
  VALUE: SYS-JE-006

[REQUIREMENT]
UID: HLR-JE-013
TITLE: JSON Escape Feature 13
STATEMENT: >>>
The JSON Escape component shall support feature variant 13.
<<<
RELATIONS:
- TYPE: Parent
  VALUE: SYS-JE-006

[REQUIREMENT]
UID: HLR-JE-014
TITLE: JSON Escape Feature 14
STATEMENT: >>>
The JSON Escape component shall support feature variant 14.
<<<
RELATIONS:
- TYPE: Parent
  VALUE: SYS-JE-006

[REQUIREMENT]
UID: HLR-JE-015
TITLE: JSON Escape Feature 15
STATEMENT: >>>
The JSON Escape component shall support feature variant 15.
<<<
RELATIONS:
- TYPE: Parent
  VALUE: SYS-JE-006

[REQUIREMENT]
UID: HLR-JE-016
TITLE: JSON Escape Feature 16
STATEMENT: >>>
The JSON Escape component shall support feature variant 16.
<<<
RELATIONS:
- TYPE: Parent
  VALUE: SYS-JE-006

[REQUIREMENT]
UID: HLR-JE-017
TITLE: JSON Escape Feature 17
STATEMENT: >>>
The JSON Escape component shall support feature variant 17.
<<<
RELATIONS:
- TYPE: Parent
  VALUE: SYS-JE-006

[REQUIREMENT]
UID: HLR-J2Y-006
TITLE: JSON to YAML Feature 6
STATEMENT: >>>
The JSON to YAML component shall support feature variant 6.
<<<
RELATIONS:
- TYPE: Parent
  VALUE: SYS-J2Y-005

[REQUIREMENT]
UID: HLR-J2Y-007
TITLE: JSON to YAML Feature 7
STATEMENT: >>>
The JSON to YAML component shall support feature variant 7.
<<<
RELATIONS:
- TYPE: Parent
  VALUE: SYS-J2Y-005

[REQUIREMENT]
UID: HLR-J2Y-008
TITLE: JSON to YAML Feature 8
STATEMENT: >>>
The JSON to YAML component shall support feature variant 8.
<<<
RELATIONS:
- TYPE: Parent
  VALUE: SYS-J2Y-005

[REQUIREMENT]
UID: HLR-J2Y-009
TITLE: JSON to YAML Feature 9
STATEMENT: >>>
The JSON to YAML component shall support feature variant 9.
<<<
RELATIONS:
- TYPE: Parent
  VALUE: SYS-J2Y-005

[REQUIREMENT]
UID: HLR-J2Y-010
TITLE: JSON to YAML Feature 10
STATEMENT: >>>
The JSON to YAML component shall support feature variant 10.
<<<
RELATIONS:
- TYPE: Parent
  VALUE: SYS-J2Y-005

[REQUIREMENT]
UID: HLR-J2Y-011
TITLE: JSON to YAML Feature 11
STATEMENT: >>>
The JSON to YAML component shall support feature variant 11.
<<<
RELATIONS:
- TYPE: Parent
  VALUE: SYS-J2Y-005

[REQUIREMENT]
UID: HLR-J2Y-012
TITLE: JSON to YAML Feature 12
STATEMENT: >>>
The JSON to YAML component shall support feature variant 12.
<<<
RELATIONS:
- TYPE: Parent
  VALUE: SYS-J2Y-005

[REQUIREMENT]
UID: HLR-J2Y-013
TITLE: JSON to YAML Feature 13
STATEMENT: >>>
The JSON to YAML component shall support feature variant 13.
<<<
RELATIONS:
- TYPE: Parent
  VALUE: SYS-J2Y-005

[REQUIREMENT]
UID: HLR-J2Y-014
TITLE: JSON to YAML Feature 14
STATEMENT: >>>
The JSON to YAML component shall support feature variant 14.
<<<
RELATIONS:
- TYPE: Parent
  VALUE: SYS-J2Y-005

[REQUIREMENT]
UID: HLR-VJ-007
TITLE: JSON Validator Feature 7
STATEMENT: >>>
The JSON Validator component shall support feature variant 7.
<<<
RELATIONS:
- TYPE: Parent
  VALUE: SYS-VJ-006

[REQUIREMENT]
UID: HLR-VJ-008
TITLE: JSON Validator Feature 8
STATEMENT: >>>
The JSON Validator component shall support feature variant 8.
<<<
RELATIONS:
- TYPE: Parent
  VALUE: SYS-VJ-006

[REQUIREMENT]
UID: HLR-VJ-009
TITLE: JSON Validator Feature 9
STATEMENT: >>>
The JSON Validator component shall support feature variant 9.
<<<
RELATIONS:
- TYPE: Parent
  VALUE: SYS-VJ-006

[REQUIREMENT]
UID: HLR-VJ-010
TITLE: JSON Validator Feature 10
STATEMENT: >>>
The JSON Validator component shall support feature variant 10.
<<<
RELATIONS:
- TYPE: Parent
  VALUE: SYS-VJ-006

[REQUIREMENT]
UID: HLR-VJ-011
TITLE: JSON Validator Feature 11
STATEMENT: >>>
The JSON Validator component shall support feature variant 11.
<<<
RELATIONS:
- TYPE: Parent
  VALUE: SYS-VJ-006

[REQUIREMENT]
UID: HLR-VJ-012
TITLE: JSON Validator Feature 12
STATEMENT: >>>
The JSON Validator component shall support feature variant 12.
<<<
RELATIONS:
- TYPE: Parent
  VALUE: SYS-VJ-006

[REQUIREMENT]
UID: HLR-VJ-013
TITLE: JSON Validator Feature 13
STATEMENT: >>>
The JSON Validator component shall support feature variant 13.
<<<
RELATIONS:
- TYPE: Parent
  VALUE: SYS-VJ-006

[REQUIREMENT]
UID: HLR-VJ-014
TITLE: JSON Validator Feature 14
STATEMENT: >>>
The JSON Validator component shall support feature variant 14.
<<<
RELATIONS:
- TYPE: Parent
  VALUE: SYS-VJ-006

[REQUIREMENT]
UID: HLR-VJ-015
TITLE: JSON Validator Feature 15
STATEMENT: >>>
The JSON Validator component shall support feature variant 15.
<<<
RELATIONS:
- TYPE: Parent
  VALUE: SYS-VJ-006

[[/SECTION]]

[[SECTION]]
TITLE: Verification Evidence, Traceability and Integration Requirements

[REQUIREMENT]
UID: HLR-VEV-001
TITLE: Exit Status Reflects Verification
STATEMENT: >>>
The verifier shall exit with a non-zero status when a test case failed, when a log could not
be verified, when a folder holds no logs, or when a test case was aborted by a failed hook.
The option that accepts failed test cases shall not hide a log that could not be verified.
<<<
RELATIONS:
- TYPE: Parent
  VALUE: SYS-VEV-001

[REQUIREMENT]
UID: HLR-VEV-002
TITLE: Test Cases Without Steps
STATEMENT: >>>
The verifier shall not report a test case without steps as passed.
<<<
RELATIONS:
- TYPE: Parent
  VALUE: SYS-VEV-001

[REQUIREMENT]
UID: HLR-VEV-003
TITLE: Entries Of Other Test Cases
STATEMENT: >>>
The verifier shall ignore, with a warning, execution log entries that name a different test
case than the one being verified.
<<<
RELATIONS:
- TYPE: Parent
  VALUE: SYS-VEV-001

[REQUIREMENT]
UID: HLR-VEV-004
TITLE: Report Destination
STATEMENT: >>>
The verifier shall write its report to the file named by the output option and to standard
output otherwise.
<<<
RELATIONS:
- TYPE: Parent
  VALUE: SYS-VER-003

[REQUIREMENT]
UID: HLR-VEV-005
TITLE: Failed Hook Entry
STATEMENT: >>>
A generated test script shall record a failed lifecycle hook in the execution log as a
complete entry that identifies the hook, so that the verifier can read it and report the
test case as errored.
<<<
RELATIONS:
- TYPE: Parent
  VALUE: SYS-VEV-001

[REQUIREMENT]
UID: HLR-RUN-001
TITLE: Log Entry Identity
STATEMENT: >>>
Every execution log entry shall carry the test case ID and, when known, the run ID.
<<<
RELATIONS:
- TYPE: Parent
  VALUE: SYS-RUN-001

[REQUIREMENT]
UID: HLR-RUN-002
TITLE: Result Metadata
STATEMENT: >>>
The verifier shall stamp the run ID, build ID, environment, tester and date on each
verification result. It shall take explicit values in the order flag, environment variable,
configuration file and execution log, and shall omit values that are absent or blank.
<<<
RELATIONS:
- TYPE: Parent
  VALUE: SYS-RUN-001

[REQUIREMENT]
UID: HLR-RUN-003
TITLE: Test Run Record
STATEMENT: >>>
The verifier shall write a test run record by default when the run ID, build ID, environment
and tester are known. The record shall give a verdict (pass, fail, not_executed or error)
per test case, the reviewer and problem reports when given, and the start and end of the
execution. A default run without those values shall warn and succeed; a run that asked for
the record shall fail.
<<<
RELATIONS:
- TYPE: Parent
  VALUE: SYS-RUN-001

[REQUIREMENT]
UID: HLR-RUN-004
TITLE: Test Classification
STATEMENT: >>>
The system shall keep on each test case its requirement IDs, test type, test category,
level, objective, environment, pass and fail criteria, author and independence flag, and
shall refuse a test category that does not belong to the test type.
<<<
RELATIONS:
- TYPE: Parent
  VALUE: SYS-TRC-001

[REQUIREMENT]
UID: HLR-TRC-001
TITLE: Traceability Matrix
STATEMENT: >>>
The system shall generate a traceability matrix relating each requirement to the test cases
that list it and to the test runs whose results exercised them.
<<<
RELATIONS:
- TYPE: Parent
  VALUE: SYS-TRC-001

[REQUIREMENT]
UID: HLR-TRC-002
TITLE: Normal-Range And Robustness Check
STATEMENT: >>>
The system shall fail, naming the requirement and the missing kind, when a high-level or
low-level requirement has no normal-range test case or no robustness test case, and shall
allow that check to be disabled.
<<<
RELATIONS:
- TYPE: Parent
  VALUE: SYS-TRC-001

[REQUIREMENT]
UID: HLR-TRC-003
TITLE: Regression Selection
STATEMENT: >>>
The system shall select the test cases to run again from the change impact of a baseline and
from the regression block of a test plan, and shall report a missing or invalid baseline.
<<<
RELATIONS:
- TYPE: Parent
  VALUE: SYS-TRC-001

[REQUIREMENT]
UID: HLR-TRC-004
TITLE: Structural Coverage Import
STATEMENT: >>>
The system shall convert the output of a structural coverage tool into a coverage report,
and shall require every coverage gap to carry a classification and a rationale.
<<<
RELATIONS:
- TYPE: Parent
  VALUE: SYS-TRC-001

[REQUIREMENT]
UID: HLR-TRC-005
TITLE: Requirement Sources
STATEMENT: >>>
The system shall read the requirement set from an identifier list, from requirement records,
or from a StrictDoc export, and shall not treat a test case that cannot be read as absent.
<<<
COMMENT: >>>
The layout of the StrictDoc JSON export is an assumption (no export sample was available);
see docs/TRACEABILITY.md and decision-1 of the backlog.
<<<
RELATIONS:
- TYPE: Parent
  VALUE: SYS-TRC-001

[REQUIREMENT]
UID: HLR-IND-001
TITLE: Reviewer Independence
STATEMENT: >>>
The system shall refuse to write a test run when a test case that requires independence has
no reviewer, has no recorded author, or has the author as reviewer.
<<<
RELATIONS:
- TYPE: Parent
  VALUE: SYS-IND-001

[REQUIREMENT]
UID: HLR-IND-002
TITLE: Independence Assignment Records
STATEMENT: >>>
The system shall create and validate independence assignment records, and shall reject a
record that declares the verifier independent when the verifier is the author.
<<<
RELATIONS:
- TYPE: Parent
  VALUE: SYS-IND-001

[REQUIREMENT]
UID: HLR-PIN-001
TITLE: Pinned Schemas
STATEMENT: >>>
The system shall keep a copy of the tcms-schemas schemas and samples pinned to a recorded
commit, and shall provide a command that updates it.
<<<
RELATIONS:
- TYPE: Parent
  VALUE: SYS-PIN-001

[REQUIREMENT]
UID: HLR-PIN-002
TITLE: Schema Resolution
STATEMENT: >>>
The system shall resolve the schema named by the schema field of a document from its own
schemas first and from the pinned copy second, and shall reject an unknown schema.
<<<
RELATIONS:
- TYPE: Parent
  VALUE: SYS-PIN-001

[REQUIREMENT]
UID: HLR-PIN-003
TITLE: Portable YAML Output
STATEMENT: >>>
The system shall write YAML that other readers read back unchanged: no language-specific
tags, and quotes around strings that would otherwise read as dates, booleans or numbers.
<<<
RELATIONS:
- TYPE: Parent
  VALUE: SYS-PIN-001

[REQUIREMENT]
UID: HLR-JIRA-001
TITLE: Identifier Resolution
STATEMENT: >>>
The system shall resolve an identifier of the issue tracker or of the requirements tool to
its URL, and a URL to its identifier, from configured patterns, and shall reject
configurations with overlapping patterns.
<<<
RELATIONS:
- TYPE: Parent
  VALUE: SYS-JIRA-001

[REQUIREMENT]
UID: HLR-JIRA-002
TITLE: Write Policy
STATEMENT: >>>
The system shall refuse, before any request is sent, a write to the issue tracker that the
configured write policy does not allow, including any change to the summary or description
of a feature.
<<<
RELATIONS:
- TYPE: Parent
  VALUE: SYS-JIRA-001

[REQUIREMENT]
UID: HLR-JIRA-003
TITLE: Acting User
STATEMENT: >>>
The system shall record the acting user in every audit entry and in every comment it writes
to the issue tracker.
<<<
RELATIONS:
- TYPE: Parent
  VALUE: SYS-JIRA-001

[REQUIREMENT]
UID: HLR-JIRA-004
TITLE: No Credentials In Records
STATEMENT: >>>
The system shall not write a credential to a record, a state file, an audit entry or a log.
<<<
RELATIONS:
- TYPE: Parent
  VALUE: SYS-JIRA-001

[REQUIREMENT]
UID: HLR-JIRA-005
TITLE: Requirement Import
STATEMENT: >>>
The system shall import requirements from exactly one configured source, the issue tracker
or StrictDoc, into requirement records, and a repeated import shall change no unchanged
record.
<<<
COMMENT: >>>
Verified against a mock issue tracker only; the StrictDoc export layout is an assumption.
See docs/JIRA_INTEGRATION.md and decision-1 of the backlog.
<<<
RELATIONS:
- TYPE: Parent
  VALUE: SYS-JIRA-001

[REQUIREMENT]
UID: HLR-JIRA-006
TITLE: Test Backends
STATEMENT: >>>
The system shall keep test cases, runs and statuses in the issue tracker through one
interface for plain Jira, Xray, Zephyr Scale and Zephyr Squad, selected by configuration
alone, and shall mark a deleted test case obsolete instead of deleting it.
<<<
COMMENT: >>>
Verified against mock servers only; the Xray, Zephyr Scale and Zephyr Squad interfaces are
assumptions from their documentation. See docs/JIRA_INTEGRATION.md and decision decision-1
of the backlog.
<<<
RELATIONS:
- TYPE: Parent
  VALUE: SYS-JIRA-001

[REQUIREMENT]
UID: HLR-JIRA-007
TITLE: Status Roll-Up
STATEMENT: >>>
The system shall write the lifecycle and latest verdict of each test case and the
verification and validation status and coverage of each feature, and an open linked defect
shall prevent a pass.
<<<
RELATIONS:
- TYPE: Parent
  VALUE: SYS-JIRA-001

[REQUIREMENT]
UID: HLR-JIRA-008
TITLE: Milestones And Defects
STATEMENT: >>>
The system shall represent a test plan as a Fix Version, and shall create or link issue
tracker issues from problem reports without creating a second issue for the same report.
<<<
RELATIONS:
- TYPE: Parent
  VALUE: SYS-JIRA-001

[REQUIREMENT]
UID: HLR-JIRA-009
TITLE: Controlled Synchronisation
STATEMENT: >>>
The system shall provide a synchronisation command that only previews its changes unless
asked to apply them, and that records the acting user and the changes made.
<<<
RELATIONS:
- TYPE: Parent
  VALUE: SYS-JIRA-001

[[/SECTION]]

[[SECTION]]
TITLE: Traceability Report Requirements

[REQUIREMENT]
UID: HLR-REP-LOAD-01
TITLE: Validated Report Inputs
STATEMENT: >>>
The system shall read the trace matrix and the test run records through schema validation, and shall fail the report run, naming the file, when an input does not validate.
<<<
RELATIONS:
- TYPE: Parent
  VALUE: SYS-REP-003

[REQUIREMENT]
UID: HLR-REP-LOAD-02
TITLE: Input Reconciliation
STATEMENT: >>>
The system shall show a reconciliation block that lists the inputs discovered, loaded and skipped with a reason, and shall not drop an input silently.
<<<
RELATIONS:
- TYPE: Parent
  VALUE: SYS-REP-003

[REQUIREMENT]
UID: HLR-REP-LOAD-03
TITLE: Latest Run Selection
STATEMENT: >>>
When several runs contain a result for the same test case, the system shall use the run with the latest start time and shall list the runs it excluded.
<<<
RELATIONS:
- TYPE: Parent
  VALUE: SYS-REP-003

[REQUIREMENT]
UID: HLR-REP-LOAD-04
TITLE: Duplicate Run Identity
STATEMENT: >>>
The system shall fail the report run when two test run records share a run ID.
<<<
RELATIONS:
- TYPE: Parent
  VALUE: SYS-REP-003

[REQUIREMENT]
UID: HLR-REP-ROLL-01
TITLE: Coverage Separate From Status
STATEMENT: >>>
The system shall show, for each requirement, test coverage (normal-range and robustness tests present) separately from its verification status.
<<<
RELATIONS:
- TYPE: Parent
  VALUE: SYS-REP-002

[REQUIREMENT]
UID: HLR-REP-ROLL-02
TITLE: Verification Status Rule
STATEMENT: >>>
The system shall derive the verification status of a requirement from its linked test case verdicts by a documented rule, and shall report a requirement as verified only when every linked test case has verdict pass.
<<<
RELATIONS:
- TYPE: Parent
  VALUE: SYS-REP-002

[REQUIREMENT]
UID: HLR-REP-ROLL-03
TITLE: Obsolete Test Cases
STATEMENT: >>>
The system shall exclude obsolete test cases from the verification roll-up and shall count them in the report header.
<<<
RELATIONS:
- TYPE: Parent
  VALUE: SYS-REP-002

[REQUIREMENT]
UID: HLR-REP-ROLL-04
TITLE: Missing Result Is Not Passed
STATEMENT: >>>
The system shall report a linked test case without a result in the selected runs as not run, and never as passed.
<<<
RELATIONS:
- TYPE: Parent
  VALUE: SYS-REP-002

[REQUIREMENT]
UID: HLR-REP-TRC-01
TITLE: Traceability View
STATEMENT: >>>
The system shall list each requirement with its linked test cases, the verdict of each test case, and the run it came from.
<<<
RELATIONS:
- TYPE: Parent
  VALUE: SYS-REP-001

[REQUIREMENT]
UID: HLR-REP-TRC-02
TITLE: Requirement Levels
STATEMENT: >>>
The system shall take requirement IDs and levels from the trace matrix and shall keep high-level and low-level requirements distinct in the report.
<<<
RELATIONS:
- TYPE: Parent
  VALUE: SYS-REP-001

[REQUIREMENT]
UID: HLR-REP-TRC-03
TITLE: Matrix Rows
STATEMENT: >>>
The system shall list only normative requirements as traceability matrix rows, grouped under a heading for their source document, and shall show a document without normative requirements as having no traceable content.
<<<
RELATIONS:
- TYPE: Parent
  VALUE: SYS-REP-001

[REQUIREMENT]
UID: HLR-REP-TRC-04
TITLE: Matrix Columns
STATEMENT: >>>
The system shall use the test types normal_range, robustness and other as traceability matrix columns in a fixed order, shall list the linked test cases with their verdicts in each cell, and shall show a column even when it is empty.
<<<
RELATIONS:
- TYPE: Parent
  VALUE: SYS-REP-001

[REQUIREMENT]
UID: HLR-REP-TRC-05
TITLE: Deterministic Order
STATEMENT: >>>
The system shall order traceability matrix rows and columns deterministically by document, requirement ID and test case ID.
<<<
RELATIONS:
- TYPE: Parent
  VALUE: SYS-REP-003

[REQUIREMENT]
UID: HLR-REP-SUM-01
TITLE: Run Summary Counts
STATEMENT: >>>
The system shall show, per run and per requirement, the counts of pass, fail, not_executed and error results and their total, with the counts summing to the total.
<<<
RELATIONS:
- TYPE: Parent
  VALUE: SYS-REP-001

[REQUIREMENT]
UID: HLR-REP-GAP-01
TITLE: Coverage Gaps
STATEMENT: >>>
The system shall list the requirements with no test cases, the requirements missing a normal-range test, the requirements missing a robustness test, and the test cases with no recorded result.
<<<
RELATIONS:
- TYPE: Parent
  VALUE: SYS-REP-001

[REQUIREMENT]
UID: HLR-REP-PRB-01
TITLE: Problem Report List
STATEMENT: >>>
The system shall list each failed and errored result with its problem report ID.
<<<
RELATIONS:
- TYPE: Parent
  VALUE: SYS-REP-001

[REQUIREMENT]
UID: HLR-REP-PRB-02
TITLE: Missing Problem Report
STATEMENT: >>>
The system shall flag each failed or errored result that has no problem report ID.
<<<
RELATIONS:
- TYPE: Parent
  VALUE: SYS-REP-001

[REQUIREMENT]
UID: HLR-REP-OUT-01
TITLE: Markdown And AsciiDoc Output
STATEMENT: >>>
The system shall render every report in Markdown and in AsciiDoc, with characters that break table cells escaped.
<<<
RELATIONS:
- TYPE: Parent
  VALUE: SYS-REP-001

[REQUIREMENT]
UID: HLR-REP-OUT-02
TITLE: Machine-Readable Output
STATEMENT: >>>
The system shall write every report as JSON or YAML that validates against a local report schema, and shall write no file when that validation fails.
<<<
RELATIONS:
- TYPE: Parent
  VALUE: SYS-PIN-001

[REQUIREMENT]
UID: HLR-REP-OUT-03
TITLE: Deterministic Output
STATEMENT: >>>
The system shall produce byte-identical output for the same inputs and the same generation time.
<<<
RELATIONS:
- TYPE: Parent
  VALUE: SYS-REP-003

[REQUIREMENT]
UID: HLR-REP-OUT-04
TITLE: Report Header
STATEMENT: >>>
The system shall record in each report header the matrix ID, baseline ID, run IDs, build IDs, environments, testers and generation time, and shall show a missing value as not recorded.
<<<
RELATIONS:
- TYPE: Parent
  VALUE: SYS-REP-003

[REQUIREMENT]
UID: HLR-REP-CLI-01
TITLE: Report Command
STATEMENT: >>>
The system shall produce the selected report kinds from a trace matrix and test run records through a report command.
<<<
RELATIONS:
- TYPE: Parent
  VALUE: SYS-REP-001

[REQUIREMENT]
UID: HLR-REP-CLI-02
TITLE: Report Exit Status
STATEMENT: >>>
The system shall exit with status 0 on success, 1 on an input or validation error, and 2 when gaps or failed results exist and the fail-on-gaps option is given.
<<<
RELATIONS:
- TYPE: Parent
  VALUE: SYS-REP-004

[[/SECTION]]
