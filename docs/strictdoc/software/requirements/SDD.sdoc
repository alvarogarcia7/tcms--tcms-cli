[DOCUMENT]
TITLE: Software Design Description
PREFIX: LLR-

[[SECTION]]
TITLE: Verifier Component Design

[REQUIREMENT]
UID: LLR-VER-001
TITLE: ExecutionLogVerifier Struct
STATEMENT: >>>
Implement ExecutionLogVerifier in testcase-verification crate with methods for
loading, parsing, and comparing execution logs against test cases.
<<<
RELATIONS:
- TYPE: Parent
  VALUE: HLR-VER-001

[REQUIREMENT]
UID: LLR-VER-002
TITLE: Pattern Matching Engine
STATEMENT: >>>
Implement output matching strategies in testcase-verification: exact match, regex
compilation and matching, JSON schema validation.
<<<
RELATIONS:
- TYPE: Parent
  VALUE: HLR-VER-002

[REQUIREMENT]
UID: LLR-VER-003
TITLE: Exit Code Comparator
STATEMENT: >>>
Implement exit code verification comparing actual vs expected with support for
numeric comparison and optional range/set matching.
<<<
RELATIONS:
- TYPE: Parent
  VALUE: HLR-VER-003

[REQUIREMENT]
UID: LLR-VER-004
TITLE: Mismatch Detail Generator
STATEMENT: >>>
Implement mismatch reporting showing line-by-line diffs and character-level
highlighting of actual vs expected output.
<<<
RELATIONS:
- TYPE: Parent
  VALUE: HLR-VER-004

[REQUIREMENT]
UID: LLR-VER-005
TITLE: Verifier Orchestrator
STATEMENT: >>>
Implement orchestration in testcase-orchestration crate processing multiple
execution logs and aggregating results.
<<<
RELATIONS:
- TYPE: Parent
  VALUE: HLR-VER-005

[[/SECTION]]

[[SECTION]]
TITLE: Test Case Content Design

[REQUIREMENT]
UID: LLR-TC-001
TITLE: TestCase Model Structure
STATEMENT: >>>
Define TestCase struct in testcase-models with fields: test_case_id, title,
description, sequences, prerequisites, environment_variables, hooks.
<<<
RELATIONS:
- TYPE: Parent
  VALUE: HLR-TC-001

[REQUIREMENT]
UID: LLR-TC-002
TITLE: TestSequence Model
STATEMENT: >>>
Define TestSequence struct containing sequence_id, name, steps list, and
variable scope management.
<<<
RELATIONS:
- TYPE: Parent
  VALUE: HLR-TC-002

[REQUIREMENT]
UID: LLR-TC-003
TITLE: TestStep Model
STATEMENT: >>>
Define TestStep struct with description, command, expected_exit_code,
expected_output, captured_variables fields.
<<<
RELATIONS:
- TYPE: Parent
  VALUE: HLR-TC-003

[REQUIREMENT]
UID: LLR-TC-004
TITLE: Variable Capture Handler
STATEMENT: >>>
Implement variable capture in testcase-execution with regex extraction and
command substitution.
<<<
RELATIONS:
- TYPE: Parent
  VALUE: HLR-TC-004

[REQUIREMENT]
UID: LLR-TC-005
TITLE: Expected Output Specification
STATEMENT: >>>
Implement ExpectedOutput struct supporting exact string, regex pattern, and
JSON schema matching types.
<<<
RELATIONS:
- TYPE: Parent
  VALUE: HLR-TC-005

[REQUIREMENT]
UID: LLR-TC-006
TITLE: Prerequisite Handler
STATEMENT: >>>
Implement prerequisite management in testcase-execution for manual and
automatic prerequisites with verification.
<<<
RELATIONS:
- TYPE: Parent
  VALUE: HLR-TC-006

[REQUIREMENT]
UID: LLR-TC-007
TITLE: Environment Variable Hydration
STATEMENT: >>>
Implement environment variable loading and validation in testcase-execution
with support for required/optional with defaults.
<<<
RELATIONS:
- TYPE: Parent
  VALUE: HLR-TC-007

[REQUIREMENT]
UID: LLR-TC-008
TITLE: Lifecycle Hook Executor
STATEMENT: >>>
Implement hook execution in testcase-execution at eight lifecycle points with
context passing and error handling.
<<<
RELATIONS:
- TYPE: Parent
  VALUE: HLR-TC-008

[[/SECTION]]

[[SECTION]]
TITLE: YAML Input/Output Design

[REQUIREMENT]
UID: LLR-YAML-001
TITLE: Schema URI Resolver
STATEMENT: >>>
Implement schema field extraction and URI resolution in testcase-common
converting URIs to file paths.
<<<
RELATIONS:
- TYPE: Parent
  VALUE: HLR-YAML-001

[REQUIREMENT]
UID: LLR-YAML-002
TITLE: Type Field Extractor
STATEMENT: >>>
Implement type field extraction from YAML for content type identification
and routing to appropriate handlers.
<<<
RELATIONS:
- TYPE: Parent
  VALUE: HLR-YAML-002

[REQUIREMENT]
UID: LLR-YAML-003
TITLE: YAML Deserializer
STATEMENT: >>>
Implement YAML deserialization in testcase-common using serde_yaml with
proper error context for parse failures.
<<<
RELATIONS:
- TYPE: Parent
  VALUE: HLR-YAML-003

[REQUIREMENT]
UID: LLR-YAML-004
TITLE: JSON Escaper
STATEMENT: >>>
Implement JSON output escaping in bash-eval with methods: jq command pipe,
json-escape binary call, shell sed fallback.
<<<
RELATIONS:
- TYPE: Parent
  VALUE: HLR-YAML-004

[REQUIREMENT]
UID: LLR-YAML-005
TITLE: YAML Serializer for Results
STATEMENT: >>>
Implement YAML serialization in testcase-verification for verification
results with proper formatting.
<<<
RELATIONS:
- TYPE: Parent
  VALUE: HLR-YAML-005

[REQUIREMENT]
UID: LLR-YAML-006
TITLE: Container YAML Builder
STATEMENT: >>>
Implement container YAML generation in testcase-verification aggregating
test data and verification results.
<<<
RELATIONS:
- TYPE: Parent
  VALUE: HLR-YAML-006

[REQUIREMENT]
UID: LLR-YAML-007
TITLE: Round-trip Preservation
STATEMENT: >>>
Ensure all TestCase fields are preserved through YAML load/serialize cycles
without information loss.
<<<
RELATIONS:
- TYPE: Parent
  VALUE: HLR-YAML-007

[[/SECTION]]

[[SECTION]]
TITLE: Test Schema Design

[REQUIREMENT]
UID: LLR-SCHEMA-001
TITLE: Schema Loader
STATEMENT: >>>
Implement schema file loading and caching in testcase-validation from
schemas/ directory.
<<<
RELATIONS:
- TYPE: Parent
  VALUE: HLR-SCHEMA-001

[REQUIREMENT]
UID: LLR-SCHEMA-002
TITLE: jsonschema Validator
STATEMENT: >>>
Use jsonschema crate in testcase-validation for constraint validation with
detailed error reporting.
<<<
RELATIONS:
- TYPE: Parent
  VALUE: HLR-SCHEMA-002

[REQUIREMENT]
UID: LLR-SCHEMA-003
TITLE: Recursive Validator
STATEMENT: >>>
Implement recursive validation traversing nested objects and validating
against nested schema definitions.
<<<
RELATIONS:
- TYPE: Parent
  VALUE: HLR-SCHEMA-003

[REQUIREMENT]
UID: LLR-SCHEMA-004
TITLE: Regex Pattern Validator
STATEMENT: >>>
Validate regex patterns and variable names against permitted formats before
accepting test case content.
<<<
RELATIONS:
- TYPE: Parent
  VALUE: HLR-SCHEMA-004

[REQUIREMENT]
UID: LLR-SCHEMA-005
TITLE: Enum Validator
STATEMENT: >>>
Validate enumerated field values (status, match_type, hook_type) against
defined enum sets in schema.
<<<
RELATIONS:
- TYPE: Parent
  VALUE: HLR-SCHEMA-005

[REQUIREMENT]
UID: LLR-SCHEMA-006
TITLE: Execution Log Validator
STATEMENT: >>>
Validate JSON execution logs against execution-log.schema.json in schema validation.
<<<
RELATIONS:
- TYPE: Parent
  VALUE: HLR-SCHEMA-006

[REQUIREMENT]
UID: LLR-SCHEMA-007
TITLE: Container Validator
STATEMENT: >>>
Validate container YAML against container.schema.json before use in
documentation generation.
<<<
RELATIONS:
- TYPE: Parent
  VALUE: HLR-SCHEMA-007

[REQUIREMENT]
UID: LLR-SCHEMA-008
TITLE: Error Message Formatter
STATEMENT: >>>
Implement validation error reporting with field path, constraint type,
expected value, and actual value.
<<<
RELATIONS:
- TYPE: Parent
  VALUE: HLR-SCHEMA-008

[[/SECTION]]

[[SECTION]]
TITLE: Executable Implementation Design

[REQUIREMENT]
UID: LLR-EXEC-VAL-001
TITLE: Validate YAML Binary
STATEMENT: >>>
Implement validate-yaml binary in validate-yaml crate using schema validation library.
<<<
RELATIONS:
- TYPE: Parent
  VALUE: HLR-EXEC-VAL-001

[REQUIREMENT]
UID: LLR-EXEC-VAL-002
TITLE: Validate JSON Binary
STATEMENT: >>>
Implement validate-json binary in validate-json crate with JSON schema validation.
<<<
RELATIONS:
- TYPE: Parent
  VALUE: HLR-EXEC-VAL-002

[REQUIREMENT]
UID: LLR-EXEC-GEN-001
TITLE: Test Executor Binary
STATEMENT: >>>
Implement test-executor binary in test-executor crate with generate and execute subcommands.
<<<
RELATIONS:
- TYPE: Parent
  VALUE: HLR-EXEC-GEN-001

[REQUIREMENT]
UID: LLR-EXEC-GEN-002
TITLE: JSON Escape Binary
STATEMENT: >>>
Implement json-escape binary in json-escape crate reading stdin and outputting escaped JSON.
<<<
RELATIONS:
- TYPE: Parent
  VALUE: HLR-EXEC-GEN-002

[REQUIREMENT]
UID: LLR-EXEC-GEN-003
TITLE: JSON to YAML Converter Binary
STATEMENT: >>>
Implement json-to-yaml binary in json-to-yaml crate with format conversion logic.
<<<
RELATIONS:
- TYPE: Parent
  VALUE: HLR-EXEC-GEN-003

[REQUIREMENT]
UID: LLR-EXEC-GEN-004
TITLE: Script Cleanup Binary
STATEMENT: >>>
Implement script-cleanup binary in script-cleanup crate with selective removal logic.
<<<
RELATIONS:
- TYPE: Parent
  VALUE: HLR-EXEC-GEN-004

[REQUIREMENT]
UID: LLR-EXEC-ORCH-001
TITLE: Test Orchestrator Binary
STATEMENT: >>>
Implement test-orchestrator binary in test-orchestrator crate with coordination logic.
<<<
RELATIONS:
- TYPE: Parent
  VALUE: HLR-EXEC-ORCH-001

[REQUIREMENT]
UID: LLR-EXEC-ORCH-002
TITLE: Testcase Manager Binary
STATEMENT: >>>
Implement testcase-manager binary in testcase-manager crate with lifecycle management.
<<<
RELATIONS:
- TYPE: Parent
  VALUE: HLR-EXEC-ORCH-002

[REQUIREMENT]
UID: LLR-EXEC-ORCH-003
TITLE: Test Run Manager Binary
STATEMENT: >>>
Implement test-run-manager binary (trm) in test-run-manager crate with tracking logic.
<<<
RELATIONS:
- TYPE: Parent
  VALUE: HLR-EXEC-ORCH-003

[REQUIREMENT]
UID: LLR-EXEC-VER-001
TITLE: Verifier Binary
STATEMENT: >>>
Implement verifier binary in verifier crate with verification and result generation.
<<<
RELATIONS:
- TYPE: Parent
  VALUE: HLR-EXEC-VER-001

[REQUIREMENT]
UID: LLR-EXEC-VER-002
TITLE: TPDG Compat Binary
STATEMENT: >>>
Implement tpdg-compat binary in tpdg-compat crate with validation and reporting.
<<<
RELATIONS:
- TYPE: Parent
  VALUE: HLR-EXEC-VER-002

[REQUIREMENT]
UID: LLR-EXEC-EDT-001
TITLE: Editor Binary
STATEMENT: >>>
Implement editor binary in editor crate with terminal UI and validation integration.
<<<
RELATIONS:
- TYPE: Parent
  VALUE: HLR-EXEC-EDT-001

[REQUIREMENT]
UID: LLR-VER-011
TITLE: Verification Implementation 11
STATEMENT: >>>
Implement verification logic variant 11 with comprehensive error handling.
<<<
RELATIONS:
- TYPE: Parent
  VALUE: HLR-VER-001

[REQUIREMENT]
UID: LLR-VER-012
TITLE: Verification Implementation 12
STATEMENT: >>>
Implement verification logic variant 12 with comprehensive error handling.
<<<
RELATIONS:
- TYPE: Parent
  VALUE: HLR-VER-001

[REQUIREMENT]
UID: LLR-VER-013
TITLE: Verification Implementation 13
STATEMENT: >>>
Implement verification logic variant 13 with comprehensive error handling.
<<<
RELATIONS:
- TYPE: Parent
  VALUE: HLR-VER-001

[REQUIREMENT]
UID: LLR-VER-014
TITLE: Verification Implementation 14
STATEMENT: >>>
Implement verification logic variant 14 with comprehensive error handling.
<<<
RELATIONS:
- TYPE: Parent
  VALUE: HLR-VER-001

[REQUIREMENT]
UID: LLR-VER-015
TITLE: Verification Implementation 15
STATEMENT: >>>
Implement verification logic variant 15 with comprehensive error handling.
<<<
RELATIONS:
- TYPE: Parent
  VALUE: HLR-VER-001

[REQUIREMENT]
UID: LLR-VER-016
TITLE: Verification Implementation 16
STATEMENT: >>>
Implement verification logic variant 16 with comprehensive error handling.
<<<
RELATIONS:
- TYPE: Parent
  VALUE: HLR-VER-001

[REQUIREMENT]
UID: LLR-VER-017
TITLE: Verification Implementation 17
STATEMENT: >>>
Implement verification logic variant 17 with comprehensive error handling.
<<<
RELATIONS:
- TYPE: Parent
  VALUE: HLR-VER-001

[REQUIREMENT]
UID: LLR-VER-018
TITLE: Verification Implementation 18
STATEMENT: >>>
Implement verification logic variant 18 with comprehensive error handling.
<<<
RELATIONS:
- TYPE: Parent
  VALUE: HLR-VER-001

[REQUIREMENT]
UID: LLR-VER-019
TITLE: Verification Implementation 19
STATEMENT: >>>
Implement verification logic variant 19 with comprehensive error handling.
<<<
RELATIONS:
- TYPE: Parent
  VALUE: HLR-VER-001

[REQUIREMENT]
UID: LLR-VER-020
TITLE: Verification Implementation 20
STATEMENT: >>>
Implement verification logic variant 20 with comprehensive error handling.
<<<
RELATIONS:
- TYPE: Parent
  VALUE: HLR-VER-001

[REQUIREMENT]
UID: LLR-VER-021
TITLE: Verification Implementation 21
STATEMENT: >>>
Implement verification logic variant 21 with comprehensive error handling.
<<<
RELATIONS:
- TYPE: Parent
  VALUE: HLR-VER-001

[REQUIREMENT]
UID: LLR-VER-022
TITLE: Verification Implementation 22
STATEMENT: >>>
Implement verification logic variant 22 with comprehensive error handling.
<<<
RELATIONS:
- TYPE: Parent
  VALUE: HLR-VER-001

[REQUIREMENT]
UID: LLR-VER-023
TITLE: Verification Implementation 23
STATEMENT: >>>
Implement verification logic variant 23 with comprehensive error handling.
<<<
RELATIONS:
- TYPE: Parent
  VALUE: HLR-VER-001

[REQUIREMENT]
UID: LLR-VER-024
TITLE: Verification Implementation 24
STATEMENT: >>>
Implement verification logic variant 24 with comprehensive error handling.
<<<
RELATIONS:
- TYPE: Parent
  VALUE: HLR-VER-001

[REQUIREMENT]
UID: LLR-VER-025
TITLE: Verification Implementation 25
STATEMENT: >>>
Implement verification logic variant 25 with comprehensive error handling.
<<<
RELATIONS:
- TYPE: Parent
  VALUE: HLR-VER-001

[REQUIREMENT]
UID: LLR-VER-026
TITLE: Verification Implementation 26
STATEMENT: >>>
Implement verification logic variant 26 with comprehensive error handling.
<<<
RELATIONS:
- TYPE: Parent
  VALUE: HLR-VER-001

[REQUIREMENT]
UID: LLR-VER-027
TITLE: Verification Implementation 27
STATEMENT: >>>
Implement verification logic variant 27 with comprehensive error handling.
<<<
RELATIONS:
- TYPE: Parent
  VALUE: HLR-VER-001

[REQUIREMENT]
UID: LLR-VER-028
TITLE: Verification Implementation 28
STATEMENT: >>>
Implement verification logic variant 28 with comprehensive error handling.
<<<
RELATIONS:
- TYPE: Parent
  VALUE: HLR-VER-001

[REQUIREMENT]
UID: LLR-VER-029
TITLE: Verification Implementation 29
STATEMENT: >>>
Implement verification logic variant 29 with comprehensive error handling.
<<<
RELATIONS:
- TYPE: Parent
  VALUE: HLR-VER-001

[REQUIREMENT]
UID: LLR-VER-030
TITLE: Verification Implementation 30
STATEMENT: >>>
Implement verification logic variant 30 with comprehensive error handling.
<<<
RELATIONS:
- TYPE: Parent
  VALUE: HLR-VER-001

[REQUIREMENT]
UID: LLR-VER-031
TITLE: Verification Implementation 31
STATEMENT: >>>
Implement verification logic variant 31 with comprehensive error handling.
<<<
RELATIONS:
- TYPE: Parent
  VALUE: HLR-VER-001

[REQUIREMENT]
UID: LLR-VER-032
TITLE: Verification Implementation 32
STATEMENT: >>>
Implement verification logic variant 32 with comprehensive error handling.
<<<
RELATIONS:
- TYPE: Parent
  VALUE: HLR-VER-001

[REQUIREMENT]
UID: LLR-VER-033
TITLE: Verification Implementation 33
STATEMENT: >>>
Implement verification logic variant 33 with comprehensive error handling.
<<<
RELATIONS:
- TYPE: Parent
  VALUE: HLR-VER-001

[REQUIREMENT]
UID: LLR-VER-034
TITLE: Verification Implementation 34
STATEMENT: >>>
Implement verification logic variant 34 with comprehensive error handling.
<<<
RELATIONS:
- TYPE: Parent
  VALUE: HLR-VER-001

[REQUIREMENT]
UID: LLR-VER-035
TITLE: Verification Implementation 35
STATEMENT: >>>
Implement verification logic variant 35 with comprehensive error handling.
<<<
RELATIONS:
- TYPE: Parent
  VALUE: HLR-VER-001

[REQUIREMENT]
UID: LLR-VER-036
TITLE: Verification Implementation 36
STATEMENT: >>>
Implement verification logic variant 36 with comprehensive error handling.
<<<
RELATIONS:
- TYPE: Parent
  VALUE: HLR-VER-001

[REQUIREMENT]
UID: LLR-VER-037
TITLE: Verification Implementation 37
STATEMENT: >>>
Implement verification logic variant 37 with comprehensive error handling.
<<<
RELATIONS:
- TYPE: Parent
  VALUE: HLR-VER-001

[REQUIREMENT]
UID: LLR-VER-038
TITLE: Verification Implementation 38
STATEMENT: >>>
Implement verification logic variant 38 with comprehensive error handling.
<<<
RELATIONS:
- TYPE: Parent
  VALUE: HLR-VER-001

[REQUIREMENT]
UID: LLR-VER-039
TITLE: Verification Implementation 39
STATEMENT: >>>
Implement verification logic variant 39 with comprehensive error handling.
<<<
RELATIONS:
- TYPE: Parent
  VALUE: HLR-VER-001

[REQUIREMENT]
UID: LLR-TC-023
TITLE: Test Case Implementation 23
STATEMENT: >>>
Implement test case processing logic variant 23.
<<<
RELATIONS:
- TYPE: Parent
  VALUE: HLR-TC-001

[REQUIREMENT]
UID: LLR-TC-024
TITLE: Test Case Implementation 24
STATEMENT: >>>
Implement test case processing logic variant 24.
<<<
RELATIONS:
- TYPE: Parent
  VALUE: HLR-TC-001

[REQUIREMENT]
UID: LLR-TC-025
TITLE: Test Case Implementation 25
STATEMENT: >>>
Implement test case processing logic variant 25.
<<<
RELATIONS:
- TYPE: Parent
  VALUE: HLR-TC-001

[REQUIREMENT]
UID: LLR-TC-026
TITLE: Test Case Implementation 26
STATEMENT: >>>
Implement test case processing logic variant 26.
<<<
RELATIONS:
- TYPE: Parent
  VALUE: HLR-TC-001

[REQUIREMENT]
UID: LLR-TC-027
TITLE: Test Case Implementation 27
STATEMENT: >>>
Implement test case processing logic variant 27.
<<<
RELATIONS:
- TYPE: Parent
  VALUE: HLR-TC-001

[REQUIREMENT]
UID: LLR-TC-028
TITLE: Test Case Implementation 28
STATEMENT: >>>
Implement test case processing logic variant 28.
<<<
RELATIONS:
- TYPE: Parent
  VALUE: HLR-TC-001

[REQUIREMENT]
UID: LLR-TC-029
TITLE: Test Case Implementation 29
STATEMENT: >>>
Implement test case processing logic variant 29.
<<<
RELATIONS:
- TYPE: Parent
  VALUE: HLR-TC-001

[REQUIREMENT]
UID: LLR-TC-030
TITLE: Test Case Implementation 30
STATEMENT: >>>
Implement test case processing logic variant 30.
<<<
RELATIONS:
- TYPE: Parent
  VALUE: HLR-TC-001

[REQUIREMENT]
UID: LLR-TC-031
TITLE: Test Case Implementation 31
STATEMENT: >>>
Implement test case processing logic variant 31.
<<<
RELATIONS:
- TYPE: Parent
  VALUE: HLR-TC-001

[REQUIREMENT]
UID: LLR-TC-032
TITLE: Test Case Implementation 32
STATEMENT: >>>
Implement test case processing logic variant 32.
<<<
RELATIONS:
- TYPE: Parent
  VALUE: HLR-TC-001

[REQUIREMENT]
UID: LLR-TC-033
TITLE: Test Case Implementation 33
STATEMENT: >>>
Implement test case processing logic variant 33.
<<<
RELATIONS:
- TYPE: Parent
  VALUE: HLR-TC-001

[REQUIREMENT]
UID: LLR-TC-034
TITLE: Test Case Implementation 34
STATEMENT: >>>
Implement test case processing logic variant 34.
<<<
RELATIONS:
- TYPE: Parent
  VALUE: HLR-TC-001

[REQUIREMENT]
UID: LLR-TC-035
TITLE: Test Case Implementation 35
STATEMENT: >>>
Implement test case processing logic variant 35.
<<<
RELATIONS:
- TYPE: Parent
  VALUE: HLR-TC-001

[REQUIREMENT]
UID: LLR-TC-036
TITLE: Test Case Implementation 36
STATEMENT: >>>
Implement test case processing logic variant 36.
<<<
RELATIONS:
- TYPE: Parent
  VALUE: HLR-TC-001

[REQUIREMENT]
UID: LLR-TC-037
TITLE: Test Case Implementation 37
STATEMENT: >>>
Implement test case processing logic variant 37.
<<<
RELATIONS:
- TYPE: Parent
  VALUE: HLR-TC-001

[REQUIREMENT]
UID: LLR-TC-038
TITLE: Test Case Implementation 38
STATEMENT: >>>
Implement test case processing logic variant 38.
<<<
RELATIONS:
- TYPE: Parent
  VALUE: HLR-TC-001

[REQUIREMENT]
UID: LLR-TC-039
TITLE: Test Case Implementation 39
STATEMENT: >>>
Implement test case processing logic variant 39.
<<<
RELATIONS:
- TYPE: Parent
  VALUE: HLR-TC-001

[REQUIREMENT]
UID: LLR-IMPL-020
TITLE: Component Implementation 20
STATEMENT: >>>
Implement core functionality variant 20 across multiple components.
<<<
RELATIONS:
- TYPE: Parent
  VALUE: HLR-INT-001

[REQUIREMENT]
UID: LLR-IMPL-021
TITLE: Component Implementation 21
STATEMENT: >>>
Implement core functionality variant 21 across multiple components.
<<<
RELATIONS:
- TYPE: Parent
  VALUE: HLR-INT-001

[REQUIREMENT]
UID: LLR-IMPL-022
TITLE: Component Implementation 22
STATEMENT: >>>
Implement core functionality variant 22 across multiple components.
<<<
RELATIONS:
- TYPE: Parent
  VALUE: HLR-INT-001

[REQUIREMENT]
UID: LLR-IMPL-023
TITLE: Component Implementation 23
STATEMENT: >>>
Implement core functionality variant 23 across multiple components.
<<<
RELATIONS:
- TYPE: Parent
  VALUE: HLR-INT-001

[REQUIREMENT]
UID: LLR-IMPL-024
TITLE: Component Implementation 24
STATEMENT: >>>
Implement core functionality variant 24 across multiple components.
<<<
RELATIONS:
- TYPE: Parent
  VALUE: HLR-INT-001

[REQUIREMENT]
UID: LLR-IMPL-025
TITLE: Component Implementation 25
STATEMENT: >>>
Implement core functionality variant 25 across multiple components.
<<<
RELATIONS:
- TYPE: Parent
  VALUE: HLR-INT-001

[REQUIREMENT]
UID: LLR-IMPL-026
TITLE: Component Implementation 26
STATEMENT: >>>
Implement core functionality variant 26 across multiple components.
<<<
RELATIONS:
- TYPE: Parent
  VALUE: HLR-INT-001

[REQUIREMENT]
UID: LLR-IMPL-027
TITLE: Component Implementation 27
STATEMENT: >>>
Implement core functionality variant 27 across multiple components.
<<<
RELATIONS:
- TYPE: Parent
  VALUE: HLR-INT-001

[REQUIREMENT]
UID: LLR-IMPL-028
TITLE: Component Implementation 28
STATEMENT: >>>
Implement core functionality variant 28 across multiple components.
<<<
RELATIONS:
- TYPE: Parent
  VALUE: HLR-INT-001

[REQUIREMENT]
UID: LLR-IMPL-029
TITLE: Component Implementation 29
STATEMENT: >>>
Implement core functionality variant 29 across multiple components.
<<<
RELATIONS:
- TYPE: Parent
  VALUE: HLR-INT-001

[REQUIREMENT]
UID: LLR-IMPL-030
TITLE: Component Implementation 30
STATEMENT: >>>
Implement core functionality variant 30 across multiple components.
<<<
RELATIONS:
- TYPE: Parent
  VALUE: HLR-INT-001

[REQUIREMENT]
UID: LLR-IMPL-031
TITLE: Component Implementation 31
STATEMENT: >>>
Implement core functionality variant 31 across multiple components.
<<<
RELATIONS:
- TYPE: Parent
  VALUE: HLR-INT-001

[REQUIREMENT]
UID: LLR-IMPL-032
TITLE: Component Implementation 32
STATEMENT: >>>
Implement core functionality variant 32 across multiple components.
<<<
RELATIONS:
- TYPE: Parent
  VALUE: HLR-INT-001

[REQUIREMENT]
UID: LLR-IMPL-033
TITLE: Component Implementation 33
STATEMENT: >>>
Implement core functionality variant 33 across multiple components.
<<<
RELATIONS:
- TYPE: Parent
  VALUE: HLR-INT-001

[REQUIREMENT]
UID: LLR-IMPL-034
TITLE: Component Implementation 34
STATEMENT: >>>
Implement core functionality variant 34 across multiple components.
<<<
RELATIONS:
- TYPE: Parent
  VALUE: HLR-INT-001

[REQUIREMENT]
UID: LLR-IMPL-035
TITLE: Component Implementation 35
STATEMENT: >>>
Implement core functionality variant 35 across multiple components.
<<<
RELATIONS:
- TYPE: Parent
  VALUE: HLR-INT-001

[REQUIREMENT]
UID: LLR-IMPL-036
TITLE: Component Implementation 36
STATEMENT: >>>
Implement core functionality variant 36 across multiple components.
<<<
RELATIONS:
- TYPE: Parent
  VALUE: HLR-INT-001

[REQUIREMENT]
UID: LLR-IMPL-037
TITLE: Component Implementation 37
STATEMENT: >>>
Implement core functionality variant 37 across multiple components.
<<<
RELATIONS:
- TYPE: Parent
  VALUE: HLR-INT-001

[REQUIREMENT]
UID: LLR-IMPL-038
TITLE: Component Implementation 38
STATEMENT: >>>
Implement core functionality variant 38 across multiple components.
<<<
RELATIONS:
- TYPE: Parent
  VALUE: HLR-INT-001

[REQUIREMENT]
UID: LLR-IMPL-039
TITLE: Component Implementation 39
STATEMENT: >>>
Implement core functionality variant 39 across multiple components.
<<<
RELATIONS:
- TYPE: Parent
  VALUE: HLR-INT-001

[REQUIREMENT]
UID: LLR-IMPL-040
TITLE: Component Implementation 40
STATEMENT: >>>
Implement core functionality variant 40 across multiple components.
<<<
RELATIONS:
- TYPE: Parent
  VALUE: HLR-INT-001

[REQUIREMENT]
UID: LLR-IMPL-041
TITLE: Component Implementation 41
STATEMENT: >>>
Implement core functionality variant 41 across multiple components.
<<<
RELATIONS:
- TYPE: Parent
  VALUE: HLR-INT-001

[REQUIREMENT]
UID: LLR-IMPL-042
TITLE: Component Implementation 42
STATEMENT: >>>
Implement core functionality variant 42 across multiple components.
<<<
RELATIONS:
- TYPE: Parent
  VALUE: HLR-INT-001

[REQUIREMENT]
UID: LLR-IMPL-043
TITLE: Component Implementation 43
STATEMENT: >>>
Implement core functionality variant 43 across multiple components.
<<<
RELATIONS:
- TYPE: Parent
  VALUE: HLR-INT-001

[REQUIREMENT]
UID: LLR-IMPL-044
TITLE: Component Implementation 44
STATEMENT: >>>
Implement core functionality variant 44 across multiple components.
<<<
RELATIONS:
- TYPE: Parent
  VALUE: HLR-INT-001

[REQUIREMENT]
UID: LLR-IMPL-045
TITLE: Component Implementation 45
STATEMENT: >>>
Implement core functionality variant 45 across multiple components.
<<<
RELATIONS:
- TYPE: Parent
  VALUE: HLR-INT-001

[REQUIREMENT]
UID: LLR-IMPL-046
TITLE: Component Implementation 46
STATEMENT: >>>
Implement core functionality variant 46 across multiple components.
<<<
RELATIONS:
- TYPE: Parent
  VALUE: HLR-INT-001

[REQUIREMENT]
UID: LLR-IMPL-047
TITLE: Component Implementation 47
STATEMENT: >>>
Implement core functionality variant 47 across multiple components.
<<<
RELATIONS:
- TYPE: Parent
  VALUE: HLR-INT-001

[REQUIREMENT]
UID: LLR-IMPL-048
TITLE: Component Implementation 48
STATEMENT: >>>
Implement core functionality variant 48 across multiple components.
<<<
RELATIONS:
- TYPE: Parent
  VALUE: HLR-INT-001

[REQUIREMENT]
UID: LLR-IMPL-049
TITLE: Component Implementation 49
STATEMENT: >>>
Implement core functionality variant 49 across multiple components.
<<<
RELATIONS:
- TYPE: Parent
  VALUE: HLR-INT-001

[[/SECTION]]

[[SECTION]]
TITLE: Verification Evidence, Traceability and Integration Design

[REQUIREMENT]
UID: LLR-VEV-001
TITLE: Exit Status Mapping
STATEMENT: >>>
The verifier binary shall map its outcome to the exit status: 1 for a failed or errored test
case, an unverifiable log, an empty folder or an unknown test case; 0 otherwise, or for
failed test cases only when success on completion is requested.
<<<
RELATIONS:
- TYPE: Parent
  VALUE: HLR-VEV-001
- TYPE: Parent
  VALUE: HLR-VEV-002
- TYPE: Parent
  VALUE: HLR-VEV-003
- TYPE: Parent
  VALUE: HLR-VEV-004

[REQUIREMENT]
UID: LLR-VEV-002
TITLE: Failed Hook Log Entry
STATEMENT: >>>
generate_hook_execution in testcase-execution shall write the failure of a hook as a log
entry with test_sequence, step, command, exit_code, output, hook_type, hook_path and the
test case and run IDs, escaping the hook command for JSON.
<<<
RELATIONS:
- TYPE: Parent
  VALUE: HLR-VEV-005

[REQUIREMENT]
UID: LLR-RUN-001
TITLE: Log Identity In Generated Scripts
STATEMENT: >>>
The generated script shall define TEST_CASE_ID and RUN_ID (TCMS_RUN_ID at run time, else the
value given to generate) and escape them with the configured JSON escaping method before
writing them to each log entry.
<<<
RELATIONS:
- TYPE: Parent
  VALUE: HLR-RUN-001

[REQUIREMENT]
UID: LLR-RUN-002
TITLE: Run Info Stamping
STATEMENT: >>>
RunInfo in testcase-verification shall hold run ID, build ID, environment, tester and date,
drop blank values, and be stamped on each result with configured values first, the result's
own second and the report's environment and generation time last.
<<<
RELATIONS:
- TYPE: Parent
  VALUE: HLR-RUN-002

[REQUIREMENT]
UID: LLR-RUN-003
TITLE: Test Run Record Builder
STATEMENT: >>>
TestRunRecord::build shall derive the verdict of each test case, require run ID, build ID,
environment and tester, check that problem reports name failed or errored test cases of the
run, and the verifier shall write it next to the report unless told not to.
<<<
RELATIONS:
- TYPE: Parent
  VALUE: HLR-RUN-003

[REQUIREMENT]
UID: LLR-RUN-004
TITLE: Classification Types
STATEMENT: >>>
testcase-models shall define the test type, test category, level and status enumerations and
TestCase::validate_classification, which names the field and the allowed categories; storage
and the executor shall call it when loading.
<<<
RELATIONS:
- TYPE: Parent
  VALUE: HLR-RUN-004

[REQUIREMENT]
UID: LLR-TRC-001
TITLE: Trace Matrix Builder
STATEMENT: >>>
build_matrix in testcase-verification shall compute for each requirement the linked test
case IDs, normal_range_covered, robustness_covered and the IDs of runs with a result other
than not_executed, ignoring obsolete test cases and the legacy requirement field.
<<<
RELATIONS:
- TYPE: Parent
  VALUE: HLR-TRC-001
- TYPE: Parent
  VALUE: HLR-TRC-002

[REQUIREMENT]
UID: LLR-TRC-002
TITLE: Regression Selector
STATEMENT: >>>
The regression module in testcase-verification shall select test cases from the change
impact of a baseline and the requirements it names, honouring the regression block of a test
plan, and return an error for a missing or invalid baseline.
<<<
RELATIONS:
- TYPE: Parent
  VALUE: HLR-TRC-003

[REQUIREMENT]
UID: LLR-TRC-003
TITLE: Coverage Importer
STATEMENT: >>>
The coverage module in testcase-verification shall read LCOV and an MC/DC side file, apply
gap annotations by location, and keep unclassified gaps out of the report while listing
them.
<<<
RELATIONS:
- TYPE: Parent
  VALUE: HLR-TRC-004

[REQUIREMENT]
UID: LLR-TRC-004
TITLE: Requirement Readers
STATEMENT: >>>
read_requirements shall read identifier lists and requirement records, the StrictDoc export
shall be read through the requirement-import crate, and the trace-matrix command shall fail
when a test case below the directory does not load.
<<<
RELATIONS:
- TYPE: Parent
  VALUE: HLR-TRC-005

[REQUIREMENT]
UID: LLR-IND-001
TITLE: Independence Checker
STATEMENT: >>>
check_run_independence and IndependenceAssignment in testcase-verification shall compare
reviewer and author ignoring case and surrounding spaces, and shall validate that a record
declaring independence names a different verifier.
<<<
RELATIONS:
- TYPE: Parent
  VALUE: HLR-IND-001
- TYPE: Parent
  VALUE: HLR-IND-002

[REQUIREMENT]
UID: LLR-PIN-001
TITLE: Schema Vendoring Script
STATEMENT: >>>
scripts/sync-tcms-schemas.sh shall copy the schemas and samples of a given tcms-schemas
commit into schemas/tcms-schemas and record the full commit in TCMS_SCHEMAS_VERSION.
<<<
RELATIONS:
- TYPE: Parent
  VALUE: HLR-PIN-001

[REQUIREMENT]
UID: LLR-PIN-002
TITLE: Schema URI Fallback
STATEMENT: >>>
resolve_schema_uri in testcase-common shall look for the schema URI under the schemas root
first and under schemas/tcms-schemas second, and shall keep the first path when neither
exists so that the error names it.
<<<
RELATIONS:
- TYPE: Parent
  VALUE: HLR-PIN-002

[REQUIREMENT]
UID: LLR-PIN-003
TITLE: YAML Output Helper
STATEMENT: >>>
testcase_common::to_yaml_string shall convert enum tags to single-key maps and prefix
strings that match a YAML 1.1 date, boolean, number or null with a marker that forces double
quotes and is removed after serialisation; step results shall be read in both map and tag
form.
<<<
RELATIONS:
- TYPE: Parent
  VALUE: HLR-PIN-003

[REQUIREMENT]
UID: LLR-JIRA-001
TITLE: Identifier Resolver
STATEMENT: >>>
The id-resolver crate shall load the systems of an integration configuration, reject
overlapping id patterns, resolve identifiers and URLs in both directions, and fill empty
external reference URLs.
<<<
RELATIONS:
- TYPE: Parent
  VALUE: HLR-JIRA-001

[REQUIREMENT]
UID: LLR-JIRA-002
TITLE: Write Guard
STATEMENT: >>>
check_write in jira-client shall be called before every write request, refuse writes outside
the write policy and fields outside the configured field list, and refuse the summary and
description of an existing issue.
<<<
RELATIONS:
- TYPE: Parent
  VALUE: HLR-JIRA-002
- TYPE: Parent
  VALUE: HLR-JIRA-004

[REQUIREMENT]
UID: LLR-JIRA-003
TITLE: Audit Entries
STATEMENT: >>>
jira-client shall create an audit-trail entry for each write naming the acting user, and the
comment body shall name the same user; the token shall be read from the environment variable
named in the configuration and never formatted into errors or debug output.
<<<
RELATIONS:
- TYPE: Parent
  VALUE: HLR-JIRA-003
- TYPE: Parent
  VALUE: HLR-JIRA-004

[REQUIREMENT]
UID: LLR-JIRA-004
TITLE: Requirement Adapters
STATEMENT: >>>
The requirement-import crate shall turn Jira feature issues and a StrictDoc JSON export into
requirement records in a stable order without import timestamps, and reject a configuration
that names both sources.
<<<
RELATIONS:
- TYPE: Parent
  VALUE: HLR-JIRA-005

[REQUIREMENT]
UID: LLR-JIRA-005
TITLE: Test Backend Trait
STATEMENT: >>>
The test-backends crate shall define one TestBackend trait implemented for plain Jira, Xray,
Zephyr Scale and Zephyr Squad, whose writes all go through one guarded context, and whose
run recording reuses the execution of the same run.
<<<
RELATIONS:
- TYPE: Parent
  VALUE: HLR-JIRA-006

[REQUIREMENT]
UID: LLR-JIRA-006
TITLE: Status And Roll-Up Writers
STATEMENT: >>>
The statuses and rollup modules shall map lifecycle and verdict to the configured fields,
log a value changed by hand as an overwrite, and compute the feature status with an open
linked defect blocking a pass.
<<<
RELATIONS:
- TYPE: Parent
  VALUE: HLR-JIRA-007

[REQUIREMENT]
UID: LLR-JIRA-007
TITLE: Milestone And Defect Writers
STATEMENT: >>>
The milestone module shall create a Fix Version once per plan and release it on completion;
the defects module shall find an existing issue by the label tcms-pr-<id> before creating
one and refuse a push that matches more than one.
<<<
RELATIONS:
- TYPE: Parent
  VALUE: HLR-JIRA-008

[REQUIREMENT]
UID: LLR-JIRA-008
TITLE: Sync Command
STATEMENT: >>>
tcms jira sync shall run import, tests, features, milestones and defects in that order,
preview by default and write only with the apply option, persist issue keys in the external
references of the records and in a state file, and write an audit file per run.
<<<
RELATIONS:
- TYPE: Parent
  VALUE: HLR-JIRA-009

[[/SECTION]]
