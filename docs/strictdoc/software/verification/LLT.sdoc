[DOCUMENT]
TITLE: Source Code Traceability
PREFIX: SRC-

[[SECTION]]
TITLE: Source Code Traceability

[REQUIREMENT]
UID: SRC-JE-001
TITLE: json-escape Binary Implementation
STATEMENT: >>>
Source code location: crates/json-escape/src/main.rs
Implements JSON string escaping with command-line interface.
<<<
RELATIONS:
- TYPE: Parent
  VALUE: HLR-JE-001

[REQUIREMENT]
UID: SRC-J2Y-001
TITLE: json-to-yaml Binary Implementation
STATEMENT: >>>
Source code location: crates/json-to-yaml/src/main.rs
Implements JSON parsing and YAML output.
<<<
RELATIONS:
- TYPE: Parent
  VALUE: HLR-J2Y-001

[REQUIREMENT]
UID: SRC-VJ-001
TITLE: validate-json Binary Implementation
STATEMENT: >>>
Source code location: crates/validate-json/src/main.rs
Implements JSON schema validation.
<<<
RELATIONS:
- TYPE: Parent
  VALUE: HLR-VJ-001

[REQUIREMENT]
UID: SRC-TEX-001
TITLE: test-executor Binary Implementation
STATEMENT: >>>
Source code location: crates/test-executor/src/main.rs
Implements test execution and script generation.
<<<
RELATIONS:
- TYPE: Parent
  VALUE: HLR-TEX-001

[REQUIREMENT]
UID: SRC-TO-001
TITLE: test-orchestrator Binary Implementation
STATEMENT: >>>
Source code location: crates/test-orchestrator/src/main.rs
Implements parallel test execution.
<<<
RELATIONS:
- TYPE: Parent
  VALUE: HLR-TO-001

[REQUIREMENT]
UID: SRC-VER-001
TITLE: verifier Binary Implementation
STATEMENT: >>>
Source code location: crates/verifier/src/main.rs
Implements execution log verification.
<<<
RELATIONS:
- TYPE: Parent
  VALUE: HLR-VER-001

[REQUIREMENT]
UID: SRC-MOD-001
TITLE: testcase-models Crate Implementation
STATEMENT: >>>
Source code location: crates/testcase-models/src/lib.rs
Implements TestCase data models.
<<<
RELATIONS:
- TYPE: Parent
  VALUE: HLR-INT-001

[REQUIREMENT]
UID: SRC-COM-001
TITLE: testcase-common Crate Implementation
STATEMENT: >>>
Source code location: crates/testcase-common/src/lib.rs
Implements shared utilities for validation.
<<<
RELATIONS:
- TYPE: Parent
  VALUE: HLR-INT-003

[REQUIREMENT]
UID: SRC-EXEC-001
TITLE: testcase-execution Crate Implementation
STATEMENT: >>>
Source code location: crates/testcase-execution/src/lib.rs
Implements script generation and execution.
<<<
RELATIONS:
- TYPE: Parent
  VALUE: HLR-TEX-001

[REQUIREMENT]
UID: SRC-VER-002
TITLE: testcase-verification Crate Implementation
STATEMENT: >>>
Source code location: crates/testcase-verification/src/lib.rs
Implements output matching and verification.
<<<
RELATIONS:
- TYPE: Parent
  VALUE: HLR-VER-001

[REQUIREMENT]
UID: SRC-VAL-001
TITLE: testcase-validation Crate Implementation
STATEMENT: >>>
Source code location: crates/testcase-validation/src/lib.rs
Implements schema validation.
<<<
RELATIONS:
- TYPE: Parent
  VALUE: HLR-SCHEMA-009

[REQUIREMENT]
UID: SRC-ORCH-001
TITLE: testcase-orchestration Crate Implementation
STATEMENT: >>>
Source code location: crates/testcase-orchestration/src/lib.rs
Implements test execution orchestration.
<<<
RELATIONS:
- TYPE: Parent
  VALUE: HLR-TO-001

[[/SECTION]]
